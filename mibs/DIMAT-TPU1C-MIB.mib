--
-- DIMAT-TPU1C-MIB.my
-- MIB generated by MG-SOFT Visual MIB Builder Version 7.0  Build 240
-- Thursday, July 11, 2024 at 12:33:47
--

--  DIMAT-TPU1C-MIB.my
-- MIB generated by MG-SOFT Visual MIB Builder Version 7.0  Build 240
-- Monday, June 03, 2024 at 17:10:24
-- 
--  DIMAT-TPU1C-MIB.my
-- MIB generated by MG-SOFT Visual MIB Builder Version 7.0  Build 240
-- Monday, June 03, 2024 at 15:04:22
-- 
--  DIMAT-TPU1C-MIB.my
-- MIB generated by MG-SOFT Visual MIB Builder Version 7.0  Build 240
-- Wednesday, April 07, 2021 at 12:59:26
-- 
--  DIMAT-TPU1C-MIB.my
-- MIB generated by MG-SOFT Visual MIB Builder Version 7.0  Build 240
-- Wednesday, April 07, 2021 at 08:26:48
-- 
--  DIMAT-TPU1C-MIB.my
-- MIB generated by MG-SOFT Visual MIB Builder Version 7.0  Build 240
-- Thursday, February 25, 2021 at 09:32:14
-- 
--  DIMAT-TPU1C-MIB.my
-- MIB generated by MG-SOFT Visual MIB Builder Version 7.0  Build 240
-- Wednesday, February 24, 2021 at 12:32:12
-- 

	DIMAT-TPU1C-MIB DEFINITIONS ::= BEGIN
 
		IMPORTS
			dimatProducts			
				FROM DIMAT-BASE-MIB			
			OBJECT-GROUP, MODULE-COMPLIANCE, NOTIFICATION-GROUP			
				FROM SNMPv2-CONF			
			IpAddress, Integer32, Unsigned32, Counter32, BITS, 
			OBJECT-TYPE, MODULE-IDENTITY, NOTIFICATION-TYPE			
				FROM SNMPv2-SMI			
			TEXTUAL-CONVENTION			
				FROM SNMPv2-TC;
	
	
--       1.3.6.1.4.1.6346.1.8
-- June 21, 2011 at 11:50 GMT
-- June 17, 2009 at 13:13 GMT
-- May 08, 2009 at 12:59 GMT
-- January 11, 2007 at 10:30 GMT
-- 1.3.6.1.4.1.6346.1.8
-- June 21, 2011 at 11:50 GMT
-- June 17, 2009 at 13:13 GMT
-- May 08, 2009 at 12:59 GMT
-- January 11, 2007 at 10:30 GMT
-- 1.3.6.1.4.1.6346.1.8
-- June 21, 2011 at 11:50 GMT
-- June 17, 2009 at 13:13 GMT
-- May 08, 2009 at 12:59 GMT
-- January 11, 2007 at 10:30 GMT
-- 1.3.6.1.4.1.6346.1.8
-- April 07, 2021 at 11:50 GMT
-- April 07, 2021 at 12:58 GMT
-- June 17, 2009 at 13:13 GMT
-- May 08, 2009 at 12:59 GMT
-- January 11, 2007 at 10:30 GMT
-- 1.3.6.1.4.1.6346.1.8
-- April 07, 2021 at 11:50 GMT
-- April 07, 2021 at 12:58 GMT
-- June 17, 2009 at 13:13 GMT
-- May 08, 2009 at 12:59 GMT
-- January 11, 2007 at 10:30 GMT
-- 1.3.6.1.4.1.6346.1.8
-- April 07, 2021 at 11:50 GMT
-- April 07, 2021 at 12:58 GMT
-- June 17, 2009 at 13:13 GMT
-- May 08, 2009 at 12:59 GMT
-- January 11, 2007 at 10:30 GMT
		-- 1.3.6.1.4.1.6346.1.8
		tpu1c MODULE-IDENTITY 
			LAST-UPDATED "202104071150Z"		-- April 07, 2021 at 11:50 GMT
			ORGANIZATION 
				"ZIV Aplicaciones y Tecnología S.L.U."
			CONTACT-INFO 
				"Email:  ziv@zivautomation.com
				Phone:  +34 94 452 2003
				Web:     www.zivautomation.com"
			DESCRIPTION 
				"Objects for management of DIMAT S.A. TPU-1 equipment."
			REVISION "202104071258Z"		-- April 07, 2021 at 12:58 GMT
			DESCRIPTION 
				"Objects for ZIV-DIMAT TPU-1 teleprotection terminal management"
			REVISION "200906171313Z"		-- June 17, 2009 at 13:13 GMT
			DESCRIPTION 
				"Changes related with new alarms/events definition"
			REVISION "200905081259Z"		-- May 08, 2009 at 12:59 GMT
			DESCRIPTION 
				"Added object description"
			REVISION "200701111030Z"		-- January 11, 2007 at 10:30 GMT
			DESCRIPTION 
				"The initial version"
			::= { dimatProducts 8 }

		
	
--
-- Textual conventions
--
	
--  Textual conventions
-- 
-- Textual conventions
-- 
-- Textual conventions
-- 
-- Textual conventions
-- 
-- Textual conventions
-- 
-- Textual conventions
-- 
		DataIpAddress ::= TEXTUAL-CONVENTION
			STATUS current
			DESCRIPTION 
				"Data type for IP adresses."
			SYNTAX IpAddress

		DataFloat ::= TEXTUAL-CONVENTION
			STATUS current
			DESCRIPTION 
				"Data type for float objects."
			SYNTAX OCTET STRING (SIZE (0..4))

		DataAction ::= TEXTUAL-CONVENTION
			STATUS current
			DESCRIPTION 
				"Description."
			SYNTAX Integer32

	
--
-- Node definitions
--
	
--  Node definitions
-- 
-- Node definitions
-- 
-- Node definitions
-- 
-- Node definitions
-- 
-- Node definitions
-- 
-- Node definitions
-- 
-- 1.3.6.1.4.1.6346.1.8.3
-- 1.3.6.1.4.1.6346.1.8.3
-- 1.3.6.1.4.1.6346.1.8.3
-- 1.3.6.1.4.1.6346.1.8.3
-- 1.3.6.1.4.1.6346.1.8.3
-- 1.3.6.1.4.1.6346.1.8.3
		-- 1.3.6.1.4.1.6346.1.8.3
		tpu1cIpNetParams OBJECT IDENTIFIER ::= { tpu1c 3 }

		
--       1.3.6.1.4.1.6346.1.8.3.1
-- 1.3.6.1.4.1.6346.1.8.3.1
-- 1.3.6.1.4.1.6346.1.8.3.1
-- 1.3.6.1.4.1.6346.1.8.3.1
-- 1.3.6.1.4.1.6346.1.8.3.1
-- 1.3.6.1.4.1.6346.1.8.3.1
		-- 1.3.6.1.4.1.6346.1.8.3.1
		tpu1cIpNetAddrTable OBJECT-TYPE
			SYNTAX SEQUENCE OF Tpu1cIpNetAddrEntry
			MAX-ACCESS not-accessible
			STATUS current
			DESCRIPTION
				"Table of IP network addresses."
			::= { tpu1cIpNetParams 1 }

		
--       1.3.6.1.4.1.6346.1.8.3.1.1
-- 1.3.6.1.4.1.6346.1.8.3.1.1
-- 1.3.6.1.4.1.6346.1.8.3.1.1
-- 1.3.6.1.4.1.6346.1.8.3.1.1
-- 1.3.6.1.4.1.6346.1.8.3.1.1
-- 1.3.6.1.4.1.6346.1.8.3.1.1
		-- 1.3.6.1.4.1.6346.1.8.3.1.1
		tpu1cIpNetAddrEntry OBJECT-TYPE
			SYNTAX Tpu1cIpNetAddrEntry
			MAX-ACCESS not-accessible
			STATUS current
			DESCRIPTION
				"IP network address table entry."
			INDEX { tpu1cIpNetAddrIndex }
			::= { tpu1cIpNetAddrTable 1 }

		
		Tpu1cIpNetAddrEntry ::=
			SEQUENCE { 
				tpu1cIpNetAddrIndex
					Integer32,
				tpu1cIpNetAddrAddr
					DataIpAddress
			 }

--       1.3.6.1.4.1.6346.1.8.3.1.1.1
-- 1.3.6.1.4.1.6346.1.8.3.1.1.1
-- 1.3.6.1.4.1.6346.1.8.3.1.1.1
-- 1.3.6.1.4.1.6346.1.8.3.1.1.1
-- 1.3.6.1.4.1.6346.1.8.3.1.1.1
-- 1.3.6.1.4.1.6346.1.8.3.1.1.1
		-- 1.3.6.1.4.1.6346.1.8.3.1.1.1
		tpu1cIpNetAddrIndex OBJECT-TYPE
			SYNTAX Integer32 (1..2)
			MAX-ACCESS not-accessible
			STATUS current
			DESCRIPTION
				"Index value of the IP address table."
			::= { tpu1cIpNetAddrEntry 1 }

		
--       1.3.6.1.4.1.6346.1.8.3.1.1.2
-- 1.3.6.1.4.1.6346.1.8.3.1.1.2
-- 1.3.6.1.4.1.6346.1.8.3.1.1.2
-- 1.3.6.1.4.1.6346.1.8.3.1.1.2
-- 1.3.6.1.4.1.6346.1.8.3.1.1.2
-- 1.3.6.1.4.1.6346.1.8.3.1.1.2
		-- 1.3.6.1.4.1.6346.1.8.3.1.1.2
		tpu1cIpNetAddrAddr OBJECT-TYPE
			SYNTAX DataIpAddress
			MAX-ACCESS read-write
			STATUS current
			DESCRIPTION
				"IP network address."
			::= { tpu1cIpNetAddrEntry 2 }

		
--       1.3.6.1.4.1.6346.1.8.3.2
-- 1.3.6.1.4.1.6346.1.8.3.2
-- 1.3.6.1.4.1.6346.1.8.3.2
-- 1.3.6.1.4.1.6346.1.8.3.2
-- 1.3.6.1.4.1.6346.1.8.3.2
-- 1.3.6.1.4.1.6346.1.8.3.2
		-- 1.3.6.1.4.1.6346.1.8.3.2
		tpu1cIpNetMaskTable OBJECT-TYPE
			SYNTAX SEQUENCE OF Tpu1cIpNetMaskEntry
			MAX-ACCESS not-accessible
			STATUS current
			DESCRIPTION
				"Table of IP network masks."
			::= { tpu1cIpNetParams 2 }

		
--       1.3.6.1.4.1.6346.1.8.3.2.1
-- 1.3.6.1.4.1.6346.1.8.3.2.1
-- 1.3.6.1.4.1.6346.1.8.3.2.1
-- 1.3.6.1.4.1.6346.1.8.3.2.1
-- 1.3.6.1.4.1.6346.1.8.3.2.1
-- 1.3.6.1.4.1.6346.1.8.3.2.1
		-- 1.3.6.1.4.1.6346.1.8.3.2.1
		tpu1cIpNetMaskEntry OBJECT-TYPE
			SYNTAX Tpu1cIpNetMaskEntry
			MAX-ACCESS not-accessible
			STATUS current
			DESCRIPTION
				"IP network mask table entry."
			INDEX { tpu1cIpNetMaskIndex }
			::= { tpu1cIpNetMaskTable 1 }

		
		Tpu1cIpNetMaskEntry ::=
			SEQUENCE { 
				tpu1cIpNetMaskIndex
					Integer32,
				tpu1cIpNetMaskMask
					DataIpAddress
			 }

--       1.3.6.1.4.1.6346.1.8.3.2.1.1
-- 1.3.6.1.4.1.6346.1.8.3.2.1.1
-- 1.3.6.1.4.1.6346.1.8.3.2.1.1
-- 1.3.6.1.4.1.6346.1.8.3.2.1.1
-- 1.3.6.1.4.1.6346.1.8.3.2.1.1
-- 1.3.6.1.4.1.6346.1.8.3.2.1.1
		-- 1.3.6.1.4.1.6346.1.8.3.2.1.1
		tpu1cIpNetMaskIndex OBJECT-TYPE
			SYNTAX Integer32 (1..2)
			MAX-ACCESS not-accessible
			STATUS current
			DESCRIPTION
				"Index value of the IP mask table."
			::= { tpu1cIpNetMaskEntry 1 }

		
--       1.3.6.1.4.1.6346.1.8.3.2.1.2
-- 1.3.6.1.4.1.6346.1.8.3.2.1.2
-- 1.3.6.1.4.1.6346.1.8.3.2.1.2
-- 1.3.6.1.4.1.6346.1.8.3.2.1.2
-- 1.3.6.1.4.1.6346.1.8.3.2.1.2
-- 1.3.6.1.4.1.6346.1.8.3.2.1.2
		-- 1.3.6.1.4.1.6346.1.8.3.2.1.2
		tpu1cIpNetMaskMask OBJECT-TYPE
			SYNTAX DataIpAddress
			MAX-ACCESS read-write
			STATUS current
			DESCRIPTION
				"IP network mask."
			::= { tpu1cIpNetMaskEntry 2 }

		
--       1.3.6.1.4.1.6346.1.8.3.3
-- 1.3.6.1.4.1.6346.1.8.3.3
-- 1.3.6.1.4.1.6346.1.8.3.3
-- 1.3.6.1.4.1.6346.1.8.3.3
-- 1.3.6.1.4.1.6346.1.8.3.3
-- 1.3.6.1.4.1.6346.1.8.3.3
		-- 1.3.6.1.4.1.6346.1.8.3.3
		tpu1cIpNetGateWay OBJECT-TYPE
			SYNTAX DataIpAddress
			MAX-ACCESS read-write
			STATUS current
			DESCRIPTION
				"IP network address of the gateway."
			::= { tpu1cIpNetParams 3 }

		
--       1.3.6.1.4.1.6346.1.8.4
-- 1.3.6.1.4.1.6346.1.8.4
-- 1.3.6.1.4.1.6346.1.8.4
-- 1.3.6.1.4.1.6346.1.8.4
-- 1.3.6.1.4.1.6346.1.8.4
-- 1.3.6.1.4.1.6346.1.8.4
		-- 1.3.6.1.4.1.6346.1.8.4
		tpu1cRealTimeClock OBJECT IDENTIFIER ::= { tpu1c 4 }

		
--       1.3.6.1.4.1.6346.1.8.4.1
-- 1.3.6.1.4.1.6346.1.8.4.1
-- 1.3.6.1.4.1.6346.1.8.4.1
-- 1.3.6.1.4.1.6346.1.8.4.1
-- 1.3.6.1.4.1.6346.1.8.4.1
-- 1.3.6.1.4.1.6346.1.8.4.1
		-- 1.3.6.1.4.1.6346.1.8.4.1
		tpu1cRtcSynchro OBJECT-TYPE
			SYNTAX INTEGER
				{
				internal(0),
				irigb(1),
				sntp(2)
				}
			MAX-ACCESS read-only
			STATUS current
			DESCRIPTION
				"Real Time Clock synchronization modes. '0': no synchronization , '1': IRIG-B synchronization , '2': SNTP synchronization ."
			::= { tpu1cRealTimeClock 1 }

		
--       1.3.6.1.4.1.6346.1.8.4.2
-- 1.3.6.1.4.1.6346.1.8.4.2
-- 1.3.6.1.4.1.6346.1.8.4.2
-- 1.3.6.1.4.1.6346.1.8.4.2
-- 1.3.6.1.4.1.6346.1.8.4.2
-- 1.3.6.1.4.1.6346.1.8.4.2
		-- 1.3.6.1.4.1.6346.1.8.4.2
		tpu1cRtcSntpServer OBJECT-TYPE
			SYNTAX DataIpAddress
			MAX-ACCESS read-only
			STATUS current
			DESCRIPTION
				"IP address of the SNTP server."
			::= { tpu1cRealTimeClock 2 }

		
--       1.3.6.1.4.1.6346.1.8.4.3
-- 1.3.6.1.4.1.6346.1.8.4.3
-- 1.3.6.1.4.1.6346.1.8.4.3
-- 1.3.6.1.4.1.6346.1.8.4.3
-- 1.3.6.1.4.1.6346.1.8.4.3
-- 1.3.6.1.4.1.6346.1.8.4.3
		-- 1.3.6.1.4.1.6346.1.8.4.3
		tpu1cRtcValue OBJECT-TYPE
			SYNTAX Unsigned32
			MAX-ACCESS read-only
			STATUS current
			DESCRIPTION
				"Real Time Clock value."
			::= { tpu1cRealTimeClock 3 }

		
--       1.3.6.1.4.1.6346.1.8.5
-- 1.3.6.1.4.1.6346.1.8.5
-- 1.3.6.1.4.1.6346.1.8.5
-- 1.3.6.1.4.1.6346.1.8.5
-- 1.3.6.1.4.1.6346.1.8.5
-- 1.3.6.1.4.1.6346.1.8.5
		-- 1.3.6.1.4.1.6346.1.8.5
		tpu1cCommands OBJECT IDENTIFIER ::= { tpu1c 5 }

		
--       1.3.6.1.4.1.6346.1.8.5.1
-- 1.3.6.1.4.1.6346.1.8.5.1
-- 1.3.6.1.4.1.6346.1.8.5.1
-- 1.3.6.1.4.1.6346.1.8.5.1
-- 1.3.6.1.4.1.6346.1.8.5.1
-- 1.3.6.1.4.1.6346.1.8.5.1
		-- 1.3.6.1.4.1.6346.1.8.5.1
		tpu1cCommandsTx OBJECT IDENTIFIER ::= { tpu1cCommands 1 }

		
--       1.3.6.1.4.1.6346.1.8.5.1.1
-- 1.3.6.1.4.1.6346.1.8.5.1.1
-- 1.3.6.1.4.1.6346.1.8.5.1.1
-- 1.3.6.1.4.1.6346.1.8.5.1.1
-- 1.3.6.1.4.1.6346.1.8.5.1.1
-- 1.3.6.1.4.1.6346.1.8.5.1.1
		-- 1.3.6.1.4.1.6346.1.8.5.1.1
		tpu1cCmdTxCurrentState OBJECT-TYPE
			SYNTAX BITS
				{
				cmd1(0),
				cmd2(1),
				cmd3(2),
				cmd4(3),
				cmd5(4),
				cmd6(5),
				cmd7(6),
				cmd8(7),
				cmd9(8),
				cmd10(9),
				cmd11(10),
				cmd12(11),
				cmd13(12),
				cmd14(13),
				cmd15(14),
				cmd16(15),
				cmd17(16),
				cmd18(17),
				cmd19(18),
				cmd20(19),
				cmd21(20),
				cmd22(21),
				cmd23(22),
				cmd24(23),
				cmd25(24),
				cmd26(25),
				cmd27(26),
				cmd28(27),
				cmd29(28),
				cmd30(29),
				cmd31(30),
				cmd32(31)
				}
			MAX-ACCESS read-only
			STATUS current
			DESCRIPTION
				"Description."
			::= { tpu1cCommandsTx 1 }

		
--       1.3.6.1.4.1.6346.1.8.5.1.2
-- 1.3.6.1.4.1.6346.1.8.5.1.2
-- 1.3.6.1.4.1.6346.1.8.5.1.2
-- 1.3.6.1.4.1.6346.1.8.5.1.2
-- 1.3.6.1.4.1.6346.1.8.5.1.2
-- 1.3.6.1.4.1.6346.1.8.5.1.2
		-- 1.3.6.1.4.1.6346.1.8.5.1.2
		tpu1cCmdTxCounterReset OBJECT-TYPE
			SYNTAX BITS
				{
				cmd1(0),
				cmd2(1),
				cmd3(2),
				cmd4(3),
				cmd5(4),
				cmd6(5),
				cmd7(6),
				cmd8(7),
				cmd9(8),
				cmd10(9),
				cmd11(10),
				cmd12(11),
				cmd13(12),
				cmd14(13),
				cmd15(14),
				cmd16(15),
				cmd17(16),
				cmd18(17),
				cmd19(18),
				cmd20(19),
				cmd21(20),
				cmd22(21),
				cmd23(22),
				cmd24(23),
				cmd25(24),
				cmd26(25),
				cmd27(26),
				cmd28(27),
				cmd29(28),
				cmd30(29),
				cmd31(30),
				cmd32(31)
				}
			MAX-ACCESS read-write
			STATUS current
			DESCRIPTION
				"Description."
			::= { tpu1cCommandsTx 2 }

		
--       1.3.6.1.4.1.6346.1.8.5.1.3
-- 1.3.6.1.4.1.6346.1.8.5.1.3
-- 1.3.6.1.4.1.6346.1.8.5.1.3
-- 1.3.6.1.4.1.6346.1.8.5.1.3
-- 1.3.6.1.4.1.6346.1.8.5.1.3
-- 1.3.6.1.4.1.6346.1.8.5.1.3
		-- 1.3.6.1.4.1.6346.1.8.5.1.3
		tpu1cCmdTxCounterValueTable OBJECT-TYPE
			SYNTAX SEQUENCE OF Tpu1cCmdTxCounterValueEntry
			MAX-ACCESS not-accessible
			STATUS current
			DESCRIPTION
				"Description."
			::= { tpu1cCommandsTx 3 }

		
--       1.3.6.1.4.1.6346.1.8.5.1.3.1
-- 1.3.6.1.4.1.6346.1.8.5.1.3.1
-- 1.3.6.1.4.1.6346.1.8.5.1.3.1
-- 1.3.6.1.4.1.6346.1.8.5.1.3.1
-- 1.3.6.1.4.1.6346.1.8.5.1.3.1
-- 1.3.6.1.4.1.6346.1.8.5.1.3.1
		-- 1.3.6.1.4.1.6346.1.8.5.1.3.1
		tpu1cCmdTxCounterValueEntry OBJECT-TYPE
			SYNTAX Tpu1cCmdTxCounterValueEntry
			MAX-ACCESS not-accessible
			STATUS current
			DESCRIPTION
				"Description."
			INDEX { tpu1cCmdTxCounterValueIndex }
			::= { tpu1cCmdTxCounterValueTable 1 }

		
		Tpu1cCmdTxCounterValueEntry ::=
			SEQUENCE { 
				tpu1cCmdTxCounterValueIndex
					Integer32,
				tpu1cCmdTxCounterValue
					Counter32
			 }

--       1.3.6.1.4.1.6346.1.8.5.1.3.1.1
-- 1.3.6.1.4.1.6346.1.8.5.1.3.1.1
-- 1.3.6.1.4.1.6346.1.8.5.1.3.1.1
-- 1.3.6.1.4.1.6346.1.8.5.1.3.1.1
-- 1.3.6.1.4.1.6346.1.8.5.1.3.1.1
-- 1.3.6.1.4.1.6346.1.8.5.1.3.1.1
		-- 1.3.6.1.4.1.6346.1.8.5.1.3.1.1
		tpu1cCmdTxCounterValueIndex OBJECT-TYPE
			SYNTAX Integer32 (1..32)
			MAX-ACCESS not-accessible
			STATUS current
			DESCRIPTION
				"Description."
			::= { tpu1cCmdTxCounterValueEntry 1 }

		
--       1.3.6.1.4.1.6346.1.8.5.1.3.1.2
-- 1.3.6.1.4.1.6346.1.8.5.1.3.1.2
-- 1.3.6.1.4.1.6346.1.8.5.1.3.1.2
-- 1.3.6.1.4.1.6346.1.8.5.1.3.1.2
-- 1.3.6.1.4.1.6346.1.8.5.1.3.1.2
-- 1.3.6.1.4.1.6346.1.8.5.1.3.1.2
		-- 1.3.6.1.4.1.6346.1.8.5.1.3.1.2
		tpu1cCmdTxCounterValue OBJECT-TYPE
			SYNTAX Counter32
			MAX-ACCESS read-only
			STATUS current
			DESCRIPTION
				"Description."
			::= { tpu1cCmdTxCounterValueEntry 2 }

		
--       1.3.6.1.4.1.6346.1.8.5.2
-- 1.3.6.1.4.1.6346.1.8.5.2
-- 1.3.6.1.4.1.6346.1.8.5.2
-- 1.3.6.1.4.1.6346.1.8.5.2
-- 1.3.6.1.4.1.6346.1.8.5.2
-- 1.3.6.1.4.1.6346.1.8.5.2
		-- 1.3.6.1.4.1.6346.1.8.5.2
		tpu1cCommandsRx OBJECT IDENTIFIER ::= { tpu1cCommands 2 }

		
--       1.3.6.1.4.1.6346.1.8.5.2.1
-- 1.3.6.1.4.1.6346.1.8.5.2.1
-- 1.3.6.1.4.1.6346.1.8.5.2.1
-- 1.3.6.1.4.1.6346.1.8.5.2.1
-- 1.3.6.1.4.1.6346.1.8.5.2.1
-- 1.3.6.1.4.1.6346.1.8.5.2.1
		-- 1.3.6.1.4.1.6346.1.8.5.2.1
		tpu1cCmdRxCurrentState OBJECT-TYPE
			SYNTAX BITS
				{
				cmd1(0),
				cmd2(1),
				cmd3(2),
				cmd4(3),
				cmd5(4),
				cmd6(5),
				cmd7(6),
				cmd8(7),
				cmd9(8),
				cmd10(9),
				cmd11(10),
				cmd12(11),
				cmd13(12),
				cmd14(13),
				cmd15(14),
				cmd16(15),
				cmd17(16),
				cmd18(17),
				cmd19(18),
				cmd20(19),
				cmd21(20),
				cmd22(21),
				cmd23(22),
				cmd24(23),
				cmd25(24),
				cmd26(25),
				cmd27(26),
				cmd28(27),
				cmd29(28),
				cmd30(29),
				cmd31(30),
				cmd32(31)
				}
			MAX-ACCESS read-only
			STATUS current
			DESCRIPTION
				"Description."
			::= { tpu1cCommandsRx 1 }

		
--       1.3.6.1.4.1.6346.1.8.5.2.2
-- 1.3.6.1.4.1.6346.1.8.5.2.2
-- 1.3.6.1.4.1.6346.1.8.5.2.2
-- 1.3.6.1.4.1.6346.1.8.5.2.2
-- 1.3.6.1.4.1.6346.1.8.5.2.2
-- 1.3.6.1.4.1.6346.1.8.5.2.2
		-- 1.3.6.1.4.1.6346.1.8.5.2.2
		tpu1cCmdRxCounterReset OBJECT-TYPE
			SYNTAX BITS
				{
				cmd1(0),
				cmd2(1),
				cmd3(2),
				cmd4(3),
				cmd5(4),
				cmd6(5),
				cmd7(6),
				cmd8(7),
				cmd9(8),
				cmd10(9),
				cmd11(10),
				cmd12(11),
				cmd13(12),
				cmd14(13),
				cmd15(14),
				cmd16(15),
				cmd17(16),
				cmd18(17),
				cmd19(18),
				cmd20(19),
				cmd21(20),
				cmd22(21),
				cmd23(22),
				cmd24(23),
				cmd25(24),
				cmd26(25),
				cmd27(26),
				cmd28(27),
				cmd29(28),
				cmd30(29),
				cmd31(30),
				cmd32(31)
				}
			MAX-ACCESS read-write
			STATUS current
			DESCRIPTION
				"Description."
			::= { tpu1cCommandsRx 2 }

		
--       1.3.6.1.4.1.6346.1.8.5.2.3
-- 1.3.6.1.4.1.6346.1.8.5.2.3
-- 1.3.6.1.4.1.6346.1.8.5.2.3
-- 1.3.6.1.4.1.6346.1.8.5.2.3
-- 1.3.6.1.4.1.6346.1.8.5.2.3
-- 1.3.6.1.4.1.6346.1.8.5.2.3
		-- 1.3.6.1.4.1.6346.1.8.5.2.3
		tpu1cCmdRxCounterValueTable OBJECT-TYPE
			SYNTAX SEQUENCE OF Tpu1cCmdRxCounterValueEntry
			MAX-ACCESS not-accessible
			STATUS current
			DESCRIPTION
				"Description."
			::= { tpu1cCommandsRx 3 }

		
--       1.3.6.1.4.1.6346.1.8.5.2.3.1
-- 1.3.6.1.4.1.6346.1.8.5.2.3.1
-- 1.3.6.1.4.1.6346.1.8.5.2.3.1
-- 1.3.6.1.4.1.6346.1.8.5.2.3.1
-- 1.3.6.1.4.1.6346.1.8.5.2.3.1
-- 1.3.6.1.4.1.6346.1.8.5.2.3.1
		-- 1.3.6.1.4.1.6346.1.8.5.2.3.1
		tpu1cCmdRxCounterValueEntry OBJECT-TYPE
			SYNTAX Tpu1cCmdRxCounterValueEntry
			MAX-ACCESS not-accessible
			STATUS current
			DESCRIPTION
				"Description."
			INDEX { tpu1cCmdRxCounterValueIndex }
			::= { tpu1cCmdRxCounterValueTable 1 }

		
		Tpu1cCmdRxCounterValueEntry ::=
			SEQUENCE { 
				tpu1cCmdRxCounterValueIndex
					Integer32,
				tpu1cCmdRxCounterValue
					Counter32
			 }

--       1.3.6.1.4.1.6346.1.8.5.2.3.1.1
-- 1.3.6.1.4.1.6346.1.8.5.2.3.1.1
-- 1.3.6.1.4.1.6346.1.8.5.2.3.1.1
-- 1.3.6.1.4.1.6346.1.8.5.2.3.1.1
-- 1.3.6.1.4.1.6346.1.8.5.2.3.1.1
-- 1.3.6.1.4.1.6346.1.8.5.2.3.1.1
		-- 1.3.6.1.4.1.6346.1.8.5.2.3.1.1
		tpu1cCmdRxCounterValueIndex OBJECT-TYPE
			SYNTAX Integer32 (1..32)
			MAX-ACCESS not-accessible
			STATUS current
			DESCRIPTION
				"Description."
			::= { tpu1cCmdRxCounterValueEntry 1 }

		
--       1.3.6.1.4.1.6346.1.8.5.2.3.1.2
-- 1.3.6.1.4.1.6346.1.8.5.2.3.1.2
-- 1.3.6.1.4.1.6346.1.8.5.2.3.1.2
-- 1.3.6.1.4.1.6346.1.8.5.2.3.1.2
-- 1.3.6.1.4.1.6346.1.8.5.2.3.1.2
-- 1.3.6.1.4.1.6346.1.8.5.2.3.1.2
		-- 1.3.6.1.4.1.6346.1.8.5.2.3.1.2
		tpu1cCmdRxCounterValue OBJECT-TYPE
			SYNTAX Counter32
			MAX-ACCESS read-only
			STATUS current
			DESCRIPTION
				"Description."
			::= { tpu1cCmdRxCounterValueEntry 2 }

		
--       1.3.6.1.4.1.6346.1.8.6
-- 1.3.6.1.4.1.6346.1.8.6
-- 1.3.6.1.4.1.6346.1.8.6
-- 1.3.6.1.4.1.6346.1.8.6
-- 1.3.6.1.4.1.6346.1.8.6
-- 1.3.6.1.4.1.6346.1.8.6
		-- 1.3.6.1.4.1.6346.1.8.6
		tpu1cInputOutputCircuits OBJECT IDENTIFIER ::= { tpu1c 6 }

		
--       1.3.6.1.4.1.6346.1.8.6.1
-- 1.3.6.1.4.1.6346.1.8.6.1
-- 1.3.6.1.4.1.6346.1.8.6.1
-- 1.3.6.1.4.1.6346.1.8.6.1
-- 1.3.6.1.4.1.6346.1.8.6.1
-- 1.3.6.1.4.1.6346.1.8.6.1
		-- 1.3.6.1.4.1.6346.1.8.6.1
		tpu1cInputCircuits OBJECT IDENTIFIER ::= { tpu1cInputOutputCircuits 1 }

		
--       1.3.6.1.4.1.6346.1.8.6.1.1
-- 1.3.6.1.4.1.6346.1.8.6.1.1
-- 1.3.6.1.4.1.6346.1.8.6.1.1
-- 1.3.6.1.4.1.6346.1.8.6.1.1
-- 1.3.6.1.4.1.6346.1.8.6.1.1
-- 1.3.6.1.4.1.6346.1.8.6.1.1
		-- 1.3.6.1.4.1.6346.1.8.6.1.1
		tpu1cCmdInputCircuitCurrentState OBJECT-TYPE
			SYNTAX BITS
				{
				inp1(0),
				inp2(1),
				inp3(2),
				inp4(3),
				inp5(4),
				inp6(5),
				inp7(6),
				inp8(7),
				inp9(8),
				inp10(9),
				inp11(10),
				inp12(11),
				inp13(12),
				inp14(13),
				inp15(14),
				inp16(15),
				inp17(16),
				inp18(17),
				inp19(18),
				inp20(19),
				inp21(20),
				inp22(21),
				inp23(22),
				inp24(23),
				inp25(24),
				inp26(25),
				inp27(26),
				inp28(27),
				inp29(28),
				inp30(29),
				inp31(30),
				inp32(31)
				}
			MAX-ACCESS read-only
			STATUS current
			DESCRIPTION
				"Description."
			::= { tpu1cInputCircuits 1 }

		
--       1.3.6.1.4.1.6346.1.8.6.1.2
-- 1.3.6.1.4.1.6346.1.8.6.1.2
-- 1.3.6.1.4.1.6346.1.8.6.1.2
-- 1.3.6.1.4.1.6346.1.8.6.1.2
-- 1.3.6.1.4.1.6346.1.8.6.1.2
-- 1.3.6.1.4.1.6346.1.8.6.1.2
		-- 1.3.6.1.4.1.6346.1.8.6.1.2
		tpu1cCmdInputCircuitCounterReset OBJECT-TYPE
			SYNTAX BITS
				{
				inp1(0),
				inp2(1),
				inp3(2),
				inp4(3),
				inp5(4),
				inp6(5),
				inp7(6),
				inp8(7),
				inp9(8),
				inp10(9),
				inp11(10),
				inp12(11),
				inp13(12),
				inp14(13),
				inp15(14),
				inp16(15),
				inp17(16),
				inp18(17),
				inp19(18),
				inp20(19),
				inp21(20),
				inp22(21),
				inp23(22),
				inp24(23),
				inp25(24),
				inp26(25),
				inp27(26),
				inp28(27),
				inp29(28),
				inp30(29),
				inp31(30),
				inp32(31)
				}
			MAX-ACCESS read-write
			STATUS current
			DESCRIPTION
				"Description."
			::= { tpu1cInputCircuits 2 }

		
--       1.3.6.1.4.1.6346.1.8.6.1.3
-- 1.3.6.1.4.1.6346.1.8.6.1.3
-- 1.3.6.1.4.1.6346.1.8.6.1.3
-- 1.3.6.1.4.1.6346.1.8.6.1.3
-- 1.3.6.1.4.1.6346.1.8.6.1.3
-- 1.3.6.1.4.1.6346.1.8.6.1.3
		-- 1.3.6.1.4.1.6346.1.8.6.1.3
		tpu1cCmdInputCircuitCounterValueTable OBJECT-TYPE
			SYNTAX SEQUENCE OF Tpu1cCmdInputCircuitCounterValueEntry
			MAX-ACCESS not-accessible
			STATUS current
			DESCRIPTION
				"Description."
			::= { tpu1cInputCircuits 3 }

		
--       1.3.6.1.4.1.6346.1.8.6.1.3.1
-- 1.3.6.1.4.1.6346.1.8.6.1.3.1
-- 1.3.6.1.4.1.6346.1.8.6.1.3.1
-- 1.3.6.1.4.1.6346.1.8.6.1.3.1
-- 1.3.6.1.4.1.6346.1.8.6.1.3.1
-- 1.3.6.1.4.1.6346.1.8.6.1.3.1
		-- 1.3.6.1.4.1.6346.1.8.6.1.3.1
		tpu1cCmdInputCircuitCounterValueEntry OBJECT-TYPE
			SYNTAX Tpu1cCmdInputCircuitCounterValueEntry
			MAX-ACCESS not-accessible
			STATUS current
			DESCRIPTION
				"Description."
			INDEX { tpu1cCmdInputCircuitCounterValueIndex }
			::= { tpu1cCmdInputCircuitCounterValueTable 1 }

		
		Tpu1cCmdInputCircuitCounterValueEntry ::=
			SEQUENCE { 
				tpu1cCmdInputCircuitCounterValueIndex
					Integer32,
				tpu1cCmdInputCircuitCounterValue
					Counter32
			 }

--       1.3.6.1.4.1.6346.1.8.6.1.3.1.1
-- 1.3.6.1.4.1.6346.1.8.6.1.3.1.1
-- 1.3.6.1.4.1.6346.1.8.6.1.3.1.1
-- 1.3.6.1.4.1.6346.1.8.6.1.3.1.1
-- 1.3.6.1.4.1.6346.1.8.6.1.3.1.1
-- 1.3.6.1.4.1.6346.1.8.6.1.3.1.1
		-- 1.3.6.1.4.1.6346.1.8.6.1.3.1.1
		tpu1cCmdInputCircuitCounterValueIndex OBJECT-TYPE
			SYNTAX Integer32 (1..32)
			MAX-ACCESS not-accessible
			STATUS current
			DESCRIPTION
				"Description."
			::= { tpu1cCmdInputCircuitCounterValueEntry 1 }

		
--       1.3.6.1.4.1.6346.1.8.6.1.3.1.2
-- 1.3.6.1.4.1.6346.1.8.6.1.3.1.2
-- 1.3.6.1.4.1.6346.1.8.6.1.3.1.2
-- 1.3.6.1.4.1.6346.1.8.6.1.3.1.2
-- 1.3.6.1.4.1.6346.1.8.6.1.3.1.2
-- 1.3.6.1.4.1.6346.1.8.6.1.3.1.2
		-- 1.3.6.1.4.1.6346.1.8.6.1.3.1.2
		tpu1cCmdInputCircuitCounterValue OBJECT-TYPE
			SYNTAX Counter32
			MAX-ACCESS read-only
			STATUS current
			DESCRIPTION
				"Description."
			::= { tpu1cCmdInputCircuitCounterValueEntry 2 }

		
--       1.3.6.1.4.1.6346.1.8.6.2
-- 1.3.6.1.4.1.6346.1.8.6.2
-- 1.3.6.1.4.1.6346.1.8.6.2
-- 1.3.6.1.4.1.6346.1.8.6.2
-- 1.3.6.1.4.1.6346.1.8.6.2
-- 1.3.6.1.4.1.6346.1.8.6.2
		-- 1.3.6.1.4.1.6346.1.8.6.2
		tpu1cOutputCircuits OBJECT IDENTIFIER ::= { tpu1cInputOutputCircuits 2 }

		
--       1.3.6.1.4.1.6346.1.8.6.2.1
-- 1.3.6.1.4.1.6346.1.8.6.2.1
-- 1.3.6.1.4.1.6346.1.8.6.2.1
-- 1.3.6.1.4.1.6346.1.8.6.2.1
-- 1.3.6.1.4.1.6346.1.8.6.2.1
-- 1.3.6.1.4.1.6346.1.8.6.2.1
		-- 1.3.6.1.4.1.6346.1.8.6.2.1
		tpu1cCmdOutputCircuitCurrentState OBJECT-TYPE
			SYNTAX BITS
				{
				out1(0),
				out2(1),
				out3(2),
				out4(3),
				out5(4),
				out6(5),
				out7(6),
				out8(7),
				out9(8),
				out10(9),
				out11(10),
				out12(11),
				out13(12),
				out14(13),
				out15(14),
				out16(15),
				out17(16),
				out18(17),
				out19(18),
				out20(19),
				out21(20),
				out22(21),
				out23(22),
				out24(23),
				out25(24),
				out26(25),
				out27(26),
				out28(27),
				out29(28),
				out30(29),
				out31(30),
				out32(31)
				}
			MAX-ACCESS read-only
			STATUS current
			DESCRIPTION
				"Description."
			::= { tpu1cOutputCircuits 1 }

		
--       1.3.6.1.4.1.6346.1.8.6.2.2
-- 1.3.6.1.4.1.6346.1.8.6.2.2
-- 1.3.6.1.4.1.6346.1.8.6.2.2
-- 1.3.6.1.4.1.6346.1.8.6.2.2
-- 1.3.6.1.4.1.6346.1.8.6.2.2
-- 1.3.6.1.4.1.6346.1.8.6.2.2
		-- 1.3.6.1.4.1.6346.1.8.6.2.2
		tpu1cCmdOutputCircuitCounterReset OBJECT-TYPE
			SYNTAX BITS
				{
				out1(0),
				out2(1),
				out3(2),
				out4(3),
				out5(4),
				out6(5),
				out7(6),
				out8(7),
				out9(8),
				out10(9),
				out11(10),
				out12(11),
				out13(12),
				out14(13),
				out15(14),
				out16(15),
				out17(16),
				out18(17),
				out19(18),
				out20(19),
				out21(20),
				out22(21),
				out23(22),
				out24(23),
				out25(24),
				out26(25),
				out27(26),
				out28(27),
				out29(28),
				out30(29),
				out31(30),
				out32(31)
				}
			MAX-ACCESS read-write
			STATUS current
			DESCRIPTION
				"Description."
			::= { tpu1cOutputCircuits 2 }

		
--       1.3.6.1.4.1.6346.1.8.6.2.3
-- 1.3.6.1.4.1.6346.1.8.6.2.3
-- 1.3.6.1.4.1.6346.1.8.6.2.3
-- 1.3.6.1.4.1.6346.1.8.6.2.3
-- 1.3.6.1.4.1.6346.1.8.6.2.3
-- 1.3.6.1.4.1.6346.1.8.6.2.3
		-- 1.3.6.1.4.1.6346.1.8.6.2.3
		tpu1cCmdOutputCircuitCounterValueTable OBJECT-TYPE
			SYNTAX SEQUENCE OF Tpu1cCmdOutputCircuitCounterValueEntry
			MAX-ACCESS not-accessible
			STATUS current
			DESCRIPTION
				"Description."
			::= { tpu1cOutputCircuits 3 }

		
--       1.3.6.1.4.1.6346.1.8.6.2.3.1
-- 1.3.6.1.4.1.6346.1.8.6.2.3.1
-- 1.3.6.1.4.1.6346.1.8.6.2.3.1
-- 1.3.6.1.4.1.6346.1.8.6.2.3.1
-- 1.3.6.1.4.1.6346.1.8.6.2.3.1
-- 1.3.6.1.4.1.6346.1.8.6.2.3.1
		-- 1.3.6.1.4.1.6346.1.8.6.2.3.1
		tpu1cCmdOutputCircuitCounterValueEntry OBJECT-TYPE
			SYNTAX Tpu1cCmdOutputCircuitCounterValueEntry
			MAX-ACCESS not-accessible
			STATUS current
			DESCRIPTION
				"Description."
			INDEX { tpu1cCmdOutputCircuitCounterValueIndex }
			::= { tpu1cCmdOutputCircuitCounterValueTable 1 }

		
		Tpu1cCmdOutputCircuitCounterValueEntry ::=
			SEQUENCE { 
				tpu1cCmdOutputCircuitCounterValueIndex
					Integer32,
				tpu1cCmdOutputCircuitCounterValue
					Counter32
			 }

--       1.3.6.1.4.1.6346.1.8.6.2.3.1.1
-- 1.3.6.1.4.1.6346.1.8.6.2.3.1.1
-- 1.3.6.1.4.1.6346.1.8.6.2.3.1.1
-- 1.3.6.1.4.1.6346.1.8.6.2.3.1.1
-- 1.3.6.1.4.1.6346.1.8.6.2.3.1.1
-- 1.3.6.1.4.1.6346.1.8.6.2.3.1.1
		-- 1.3.6.1.4.1.6346.1.8.6.2.3.1.1
		tpu1cCmdOutputCircuitCounterValueIndex OBJECT-TYPE
			SYNTAX Integer32 (1..32)
			MAX-ACCESS not-accessible
			STATUS current
			DESCRIPTION
				"Description."
			::= { tpu1cCmdOutputCircuitCounterValueEntry 1 }

		
--       1.3.6.1.4.1.6346.1.8.6.2.3.1.2
-- 1.3.6.1.4.1.6346.1.8.6.2.3.1.2
-- 1.3.6.1.4.1.6346.1.8.6.2.3.1.2
-- 1.3.6.1.4.1.6346.1.8.6.2.3.1.2
-- 1.3.6.1.4.1.6346.1.8.6.2.3.1.2
-- 1.3.6.1.4.1.6346.1.8.6.2.3.1.2
		-- 1.3.6.1.4.1.6346.1.8.6.2.3.1.2
		tpu1cCmdOutputCircuitCounterValue OBJECT-TYPE
			SYNTAX Counter32
			MAX-ACCESS read-only
			STATUS current
			DESCRIPTION
				"Description."
			::= { tpu1cCmdOutputCircuitCounterValueEntry 2 }

		
--       1.3.6.1.4.1.6346.1.8.7
-- 1.3.6.1.4.1.6346.1.8.7
-- 1.3.6.1.4.1.6346.1.8.7
-- 1.3.6.1.4.1.6346.1.8.7
-- 1.3.6.1.4.1.6346.1.8.7
-- 1.3.6.1.4.1.6346.1.8.7
		-- 1.3.6.1.4.1.6346.1.8.7
		tpu1cTelemetry OBJECT IDENTIFIER ::= { tpu1c 7 }

		
--       1.3.6.1.4.1.6346.1.8.7.1
-- 1.3.6.1.4.1.6346.1.8.7.1
-- 1.3.6.1.4.1.6346.1.8.7.1
-- 1.3.6.1.4.1.6346.1.8.7.1
-- 1.3.6.1.4.1.6346.1.8.7.1
-- 1.3.6.1.4.1.6346.1.8.7.1
		-- 1.3.6.1.4.1.6346.1.8.7.1
		tpu1cTelemetryDigitalInputs OBJECT IDENTIFIER ::= { tpu1cTelemetry 1 }

		
--       1.3.6.1.4.1.6346.1.8.7.1.1
-- 1.3.6.1.4.1.6346.1.8.7.1.1
-- 1.3.6.1.4.1.6346.1.8.7.1.1
-- 1.3.6.1.4.1.6346.1.8.7.1.1
-- 1.3.6.1.4.1.6346.1.8.7.1.1
-- 1.3.6.1.4.1.6346.1.8.7.1.1
		-- 1.3.6.1.4.1.6346.1.8.7.1.1
		tpu1cTelemetryDigitalInputCurrentState OBJECT-TYPE
			SYNTAX BITS
				{
				inp1(0),
				inp2(1),
				inp3(2),
				inp4(3),
				inp5(4),
				inp6(5),
				inp7(6),
				inp8(7),
				inp9(8),
				inp10(9),
				inp11(10),
				inp12(11)
				}
			MAX-ACCESS read-only
			STATUS current
			DESCRIPTION
				"Description."
			::= { tpu1cTelemetryDigitalInputs 1 }

		
--       1.3.6.1.4.1.6346.1.8.7.1.2
-- 1.3.6.1.4.1.6346.1.8.7.1.2
-- 1.3.6.1.4.1.6346.1.8.7.1.2
-- 1.3.6.1.4.1.6346.1.8.7.1.2
-- 1.3.6.1.4.1.6346.1.8.7.1.2
-- 1.3.6.1.4.1.6346.1.8.7.1.2
		-- 1.3.6.1.4.1.6346.1.8.7.1.2
		tpu1cTelemetryDigitalInputCounterReset OBJECT-TYPE
			SYNTAX BITS
				{
				inp1(0),
				inp2(1),
				inp3(2),
				inp4(3),
				inp5(4),
				inp6(5),
				inp7(6),
				inp8(7),
				inp9(8),
				inp10(9),
				inp11(10),
				inp12(11)
				}
			MAX-ACCESS read-write
			STATUS current
			DESCRIPTION
				"Description."
			::= { tpu1cTelemetryDigitalInputs 2 }

		
--       1.3.6.1.4.1.6346.1.8.7.1.3
-- 1.3.6.1.4.1.6346.1.8.7.1.3
-- 1.3.6.1.4.1.6346.1.8.7.1.3
-- 1.3.6.1.4.1.6346.1.8.7.1.3
-- 1.3.6.1.4.1.6346.1.8.7.1.3
-- 1.3.6.1.4.1.6346.1.8.7.1.3
		-- 1.3.6.1.4.1.6346.1.8.7.1.3
		tpu1cTelemetryDigitalInputCounterValueTable OBJECT-TYPE
			SYNTAX SEQUENCE OF Tpu1cTelemetryDigitalInputCounterValueEntry
			MAX-ACCESS not-accessible
			STATUS current
			DESCRIPTION
				"Description."
			::= { tpu1cTelemetryDigitalInputs 3 }

		
--       1.3.6.1.4.1.6346.1.8.7.1.3.1
-- 1.3.6.1.4.1.6346.1.8.7.1.3.1
-- 1.3.6.1.4.1.6346.1.8.7.1.3.1
-- 1.3.6.1.4.1.6346.1.8.7.1.3.1
-- 1.3.6.1.4.1.6346.1.8.7.1.3.1
-- 1.3.6.1.4.1.6346.1.8.7.1.3.1
		-- 1.3.6.1.4.1.6346.1.8.7.1.3.1
		tpu1cTelemetryDigitalInputCounterValueEntry OBJECT-TYPE
			SYNTAX Tpu1cTelemetryDigitalInputCounterValueEntry
			MAX-ACCESS not-accessible
			STATUS current
			DESCRIPTION
				"Description."
			INDEX { tpu1cTelemetryDigitalInputCounterValueIndex }
			::= { tpu1cTelemetryDigitalInputCounterValueTable 1 }

		
		Tpu1cTelemetryDigitalInputCounterValueEntry ::=
			SEQUENCE { 
				tpu1cTelemetryDigitalInputCounterValueIndex
					Integer32,
				tpu1cTelemetryDigitalInputCounterValue
					Counter32
			 }

--       1.3.6.1.4.1.6346.1.8.7.1.3.1.1
-- 1.3.6.1.4.1.6346.1.8.7.1.3.1.1
-- 1.3.6.1.4.1.6346.1.8.7.1.3.1.1
-- 1.3.6.1.4.1.6346.1.8.7.1.3.1.1
-- 1.3.6.1.4.1.6346.1.8.7.1.3.1.1
-- 1.3.6.1.4.1.6346.1.8.7.1.3.1.1
		-- 1.3.6.1.4.1.6346.1.8.7.1.3.1.1
		tpu1cTelemetryDigitalInputCounterValueIndex OBJECT-TYPE
			SYNTAX Integer32 (1..12)
			MAX-ACCESS not-accessible
			STATUS current
			DESCRIPTION
				"Description."
			::= { tpu1cTelemetryDigitalInputCounterValueEntry 1 }

		
--       1.3.6.1.4.1.6346.1.8.7.1.3.1.2
-- 1.3.6.1.4.1.6346.1.8.7.1.3.1.2
-- 1.3.6.1.4.1.6346.1.8.7.1.3.1.2
-- 1.3.6.1.4.1.6346.1.8.7.1.3.1.2
-- 1.3.6.1.4.1.6346.1.8.7.1.3.1.2
-- 1.3.6.1.4.1.6346.1.8.7.1.3.1.2
		-- 1.3.6.1.4.1.6346.1.8.7.1.3.1.2
		tpu1cTelemetryDigitalInputCounterValue OBJECT-TYPE
			SYNTAX Counter32
			MAX-ACCESS read-only
			STATUS current
			DESCRIPTION
				"Description."
			::= { tpu1cTelemetryDigitalInputCounterValueEntry 2 }

		
--       1.3.6.1.4.1.6346.1.8.7.2
-- 1.3.6.1.4.1.6346.1.8.7.2
-- 1.3.6.1.4.1.6346.1.8.7.2
-- 1.3.6.1.4.1.6346.1.8.7.2
-- 1.3.6.1.4.1.6346.1.8.7.2
-- 1.3.6.1.4.1.6346.1.8.7.2
		-- 1.3.6.1.4.1.6346.1.8.7.2
		tpu1cTelemetryDigitalOutputs OBJECT IDENTIFIER ::= { tpu1cTelemetry 2 }

		
--       1.3.6.1.4.1.6346.1.8.7.2.1
-- 1.3.6.1.4.1.6346.1.8.7.2.1
-- 1.3.6.1.4.1.6346.1.8.7.2.1
-- 1.3.6.1.4.1.6346.1.8.7.2.1
-- 1.3.6.1.4.1.6346.1.8.7.2.1
-- 1.3.6.1.4.1.6346.1.8.7.2.1
		-- 1.3.6.1.4.1.6346.1.8.7.2.1
		tpu1cTelemetryDigitalOutputCurrentState OBJECT-TYPE
			SYNTAX BITS
				{
				out1(0),
				out2(1),
				out3(2),
				out4(3),
				out5(4),
				out6(5),
				out7(6),
				out8(7),
				out9(8),
				out10(9),
				out11(10),
				out12(11)
				}
			MAX-ACCESS read-only
			STATUS current
			DESCRIPTION
				"Description."
			::= { tpu1cTelemetryDigitalOutputs 1 }

		
--       1.3.6.1.4.1.6346.1.8.7.2.2
-- 1.3.6.1.4.1.6346.1.8.7.2.2
-- 1.3.6.1.4.1.6346.1.8.7.2.2
-- 1.3.6.1.4.1.6346.1.8.7.2.2
-- 1.3.6.1.4.1.6346.1.8.7.2.2
-- 1.3.6.1.4.1.6346.1.8.7.2.2
		-- 1.3.6.1.4.1.6346.1.8.7.2.2
		tpu1cTelemetryDigitalOutputCounterReset OBJECT-TYPE
			SYNTAX BITS
				{
				out1(0),
				out2(1),
				out3(2),
				out4(3),
				out5(4),
				out6(5),
				out7(6),
				out8(7),
				out9(8),
				out10(9),
				out11(10),
				out12(11)
				}
			MAX-ACCESS read-write
			STATUS current
			DESCRIPTION
				"Description."
			::= { tpu1cTelemetryDigitalOutputs 2 }

		
--       1.3.6.1.4.1.6346.1.8.7.2.3
-- 1.3.6.1.4.1.6346.1.8.7.2.3
-- 1.3.6.1.4.1.6346.1.8.7.2.3
-- 1.3.6.1.4.1.6346.1.8.7.2.3
-- 1.3.6.1.4.1.6346.1.8.7.2.3
-- 1.3.6.1.4.1.6346.1.8.7.2.3
		-- 1.3.6.1.4.1.6346.1.8.7.2.3
		tpu1cTelemetryDigitalOutputCounterValueTable OBJECT-TYPE
			SYNTAX SEQUENCE OF Tpu1cTelemetryDigitalOutputCounterValueEntry
			MAX-ACCESS not-accessible
			STATUS current
			DESCRIPTION
				"Description."
			::= { tpu1cTelemetryDigitalOutputs 3 }

		
--       1.3.6.1.4.1.6346.1.8.7.2.3.1
-- 1.3.6.1.4.1.6346.1.8.7.2.3.1
-- 1.3.6.1.4.1.6346.1.8.7.2.3.1
-- 1.3.6.1.4.1.6346.1.8.7.2.3.1
-- 1.3.6.1.4.1.6346.1.8.7.2.3.1
-- 1.3.6.1.4.1.6346.1.8.7.2.3.1
		-- 1.3.6.1.4.1.6346.1.8.7.2.3.1
		tpu1cTelemetryDigitalOutputCounterValueEntry OBJECT-TYPE
			SYNTAX Tpu1cTelemetryDigitalOutputCounterValueEntry
			MAX-ACCESS not-accessible
			STATUS current
			DESCRIPTION
				"Description."
			INDEX { tpu1cTelemetryDigitalOutputCounterValueIndex }
			::= { tpu1cTelemetryDigitalOutputCounterValueTable 1 }

		
		Tpu1cTelemetryDigitalOutputCounterValueEntry ::=
			SEQUENCE { 
				tpu1cTelemetryDigitalOutputCounterValueIndex
					Integer32,
				tpu1cTelemetryDigitalOutputCounterValue
					Counter32
			 }

--       1.3.6.1.4.1.6346.1.8.7.2.3.1.1
-- 1.3.6.1.4.1.6346.1.8.7.2.3.1.1
-- 1.3.6.1.4.1.6346.1.8.7.2.3.1.1
-- 1.3.6.1.4.1.6346.1.8.7.2.3.1.1
-- 1.3.6.1.4.1.6346.1.8.7.2.3.1.1
-- 1.3.6.1.4.1.6346.1.8.7.2.3.1.1
		-- 1.3.6.1.4.1.6346.1.8.7.2.3.1.1
		tpu1cTelemetryDigitalOutputCounterValueIndex OBJECT-TYPE
			SYNTAX Integer32 (1..12)
			MAX-ACCESS not-accessible
			STATUS current
			DESCRIPTION
				"Description."
			::= { tpu1cTelemetryDigitalOutputCounterValueEntry 1 }

		
--       1.3.6.1.4.1.6346.1.8.7.2.3.1.2
-- 1.3.6.1.4.1.6346.1.8.7.2.3.1.2
-- 1.3.6.1.4.1.6346.1.8.7.2.3.1.2
-- 1.3.6.1.4.1.6346.1.8.7.2.3.1.2
-- 1.3.6.1.4.1.6346.1.8.7.2.3.1.2
-- 1.3.6.1.4.1.6346.1.8.7.2.3.1.2
		-- 1.3.6.1.4.1.6346.1.8.7.2.3.1.2
		tpu1cTelemetryDigitalOutputCounterValue OBJECT-TYPE
			SYNTAX Counter32
			MAX-ACCESS read-only
			STATUS current
			DESCRIPTION
				"Description."
			::= { tpu1cTelemetryDigitalOutputCounterValueEntry 2 }

		
--       1.3.6.1.4.1.6346.1.8.7.3
-- 1.3.6.1.4.1.6346.1.8.7.3
-- 1.3.6.1.4.1.6346.1.8.7.3
-- 1.3.6.1.4.1.6346.1.8.7.3
-- 1.3.6.1.4.1.6346.1.8.7.3
-- 1.3.6.1.4.1.6346.1.8.7.3
		-- 1.3.6.1.4.1.6346.1.8.7.3
		tpu1cTelemetryAnalogInputs OBJECT IDENTIFIER ::= { tpu1cTelemetry 3 }

		
--       1.3.6.1.4.1.6346.1.8.7.3.1
-- 1.3.6.1.4.1.6346.1.8.7.3.1
-- 1.3.6.1.4.1.6346.1.8.7.3.1
-- 1.3.6.1.4.1.6346.1.8.7.3.1
-- 1.3.6.1.4.1.6346.1.8.7.3.1
-- 1.3.6.1.4.1.6346.1.8.7.3.1
		-- 1.3.6.1.4.1.6346.1.8.7.3.1
		tpu1cTelemetryAnalogInputCurValueTable OBJECT-TYPE
			SYNTAX SEQUENCE OF Tpu1cTelemetryAnalogInputCurValueEntry
			MAX-ACCESS not-accessible
			STATUS current
			DESCRIPTION
				"Description."
			::= { tpu1cTelemetryAnalogInputs 1 }

		
--       1.3.6.1.4.1.6346.1.8.7.3.1.1
-- 1.3.6.1.4.1.6346.1.8.7.3.1.1
-- 1.3.6.1.4.1.6346.1.8.7.3.1.1
-- 1.3.6.1.4.1.6346.1.8.7.3.1.1
-- 1.3.6.1.4.1.6346.1.8.7.3.1.1
-- 1.3.6.1.4.1.6346.1.8.7.3.1.1
		-- 1.3.6.1.4.1.6346.1.8.7.3.1.1
		tpu1cTelemetryAnalogInputCurValueEntry OBJECT-TYPE
			SYNTAX Tpu1cTelemetryAnalogInputCurValueEntry
			MAX-ACCESS not-accessible
			STATUS current
			DESCRIPTION
				"Description."
			INDEX { tpu1cTelemetryAnalogInputCurValueIndex }
			::= { tpu1cTelemetryAnalogInputCurValueTable 1 }

		
		Tpu1cTelemetryAnalogInputCurValueEntry ::=
			SEQUENCE { 
				tpu1cTelemetryAnalogInputCurValueIndex
					Integer32,
				tpu1cTelemetryAnalogInputCurValue
					DataFloat
			 }

--       1.3.6.1.4.1.6346.1.8.7.3.1.1.1
-- 1.3.6.1.4.1.6346.1.8.7.3.1.1.1
-- 1.3.6.1.4.1.6346.1.8.7.3.1.1.1
-- 1.3.6.1.4.1.6346.1.8.7.3.1.1.1
-- 1.3.6.1.4.1.6346.1.8.7.3.1.1.1
-- 1.3.6.1.4.1.6346.1.8.7.3.1.1.1
		-- 1.3.6.1.4.1.6346.1.8.7.3.1.1.1
		tpu1cTelemetryAnalogInputCurValueIndex OBJECT-TYPE
			SYNTAX Integer32 (1..12)
			MAX-ACCESS not-accessible
			STATUS current
			DESCRIPTION
				"Description."
			::= { tpu1cTelemetryAnalogInputCurValueEntry 1 }

		
--       1.3.6.1.4.1.6346.1.8.7.3.1.1.2
-- 1.3.6.1.4.1.6346.1.8.7.3.1.1.2
-- 1.3.6.1.4.1.6346.1.8.7.3.1.1.2
-- 1.3.6.1.4.1.6346.1.8.7.3.1.1.2
-- 1.3.6.1.4.1.6346.1.8.7.3.1.1.2
-- 1.3.6.1.4.1.6346.1.8.7.3.1.1.2
		-- 1.3.6.1.4.1.6346.1.8.7.3.1.1.2
		tpu1cTelemetryAnalogInputCurValue OBJECT-TYPE
			SYNTAX DataFloat
			MAX-ACCESS read-only
			STATUS current
			DESCRIPTION
				"Description."
			::= { tpu1cTelemetryAnalogInputCurValueEntry 2 }

		
--       1.3.6.1.4.1.6346.1.8.7.3.2
-- 1.3.6.1.4.1.6346.1.8.7.3.2
-- 1.3.6.1.4.1.6346.1.8.7.3.2
-- 1.3.6.1.4.1.6346.1.8.7.3.2
-- 1.3.6.1.4.1.6346.1.8.7.3.2
-- 1.3.6.1.4.1.6346.1.8.7.3.2
		-- 1.3.6.1.4.1.6346.1.8.7.3.2
		tpu1cTelemetryAnalogInputMaxValueTable OBJECT-TYPE
			SYNTAX SEQUENCE OF Tpu1cTelemetryAnalogInputMaxValueEntry
			MAX-ACCESS not-accessible
			STATUS current
			DESCRIPTION
				"Description."
			::= { tpu1cTelemetryAnalogInputs 2 }

		
--       1.3.6.1.4.1.6346.1.8.7.3.2.1
-- 1.3.6.1.4.1.6346.1.8.7.3.2.1
-- 1.3.6.1.4.1.6346.1.8.7.3.2.1
-- 1.3.6.1.4.1.6346.1.8.7.3.2.1
-- 1.3.6.1.4.1.6346.1.8.7.3.2.1
-- 1.3.6.1.4.1.6346.1.8.7.3.2.1
		-- 1.3.6.1.4.1.6346.1.8.7.3.2.1
		tpu1cTelemetryAnalogInputMaxValueEntry OBJECT-TYPE
			SYNTAX Tpu1cTelemetryAnalogInputMaxValueEntry
			MAX-ACCESS not-accessible
			STATUS current
			DESCRIPTION
				"Description."
			INDEX { tpu1cTelemetryAnalogInputMaxValueIndex }
			::= { tpu1cTelemetryAnalogInputMaxValueTable 1 }

		
		Tpu1cTelemetryAnalogInputMaxValueEntry ::=
			SEQUENCE { 
				tpu1cTelemetryAnalogInputMaxValueIndex
					Integer32,
				tpu1cTelemetryAnalogInputMaxValue
					DataFloat
			 }

--       1.3.6.1.4.1.6346.1.8.7.3.2.1.1
-- 1.3.6.1.4.1.6346.1.8.7.3.2.1.1
-- 1.3.6.1.4.1.6346.1.8.7.3.2.1.1
-- 1.3.6.1.4.1.6346.1.8.7.3.2.1.1
-- 1.3.6.1.4.1.6346.1.8.7.3.2.1.1
-- 1.3.6.1.4.1.6346.1.8.7.3.2.1.1
		-- 1.3.6.1.4.1.6346.1.8.7.3.2.1.1
		tpu1cTelemetryAnalogInputMaxValueIndex OBJECT-TYPE
			SYNTAX Integer32 (1..12)
			MAX-ACCESS not-accessible
			STATUS current
			DESCRIPTION
				"Description."
			::= { tpu1cTelemetryAnalogInputMaxValueEntry 1 }

		
--       1.3.6.1.4.1.6346.1.8.7.3.2.1.2
-- 1.3.6.1.4.1.6346.1.8.7.3.2.1.2
-- 1.3.6.1.4.1.6346.1.8.7.3.2.1.2
-- 1.3.6.1.4.1.6346.1.8.7.3.2.1.2
-- 1.3.6.1.4.1.6346.1.8.7.3.2.1.2
-- 1.3.6.1.4.1.6346.1.8.7.3.2.1.2
		-- 1.3.6.1.4.1.6346.1.8.7.3.2.1.2
		tpu1cTelemetryAnalogInputMaxValue OBJECT-TYPE
			SYNTAX DataFloat
			MAX-ACCESS read-only
			STATUS current
			DESCRIPTION
				"Description."
			::= { tpu1cTelemetryAnalogInputMaxValueEntry 2 }

		
--       1.3.6.1.4.1.6346.1.8.7.3.3
-- 1.3.6.1.4.1.6346.1.8.7.3.3
-- 1.3.6.1.4.1.6346.1.8.7.3.3
-- 1.3.6.1.4.1.6346.1.8.7.3.3
-- 1.3.6.1.4.1.6346.1.8.7.3.3
-- 1.3.6.1.4.1.6346.1.8.7.3.3
		-- 1.3.6.1.4.1.6346.1.8.7.3.3
		tpu1cTelemetryAnalogInputMinValueTable OBJECT-TYPE
			SYNTAX SEQUENCE OF Tpu1cTelemetryAnalogInputMinValueEntry
			MAX-ACCESS not-accessible
			STATUS current
			DESCRIPTION
				"Description."
			::= { tpu1cTelemetryAnalogInputs 3 }

		
--       1.3.6.1.4.1.6346.1.8.7.3.3.1
-- 1.3.6.1.4.1.6346.1.8.7.3.3.1
-- 1.3.6.1.4.1.6346.1.8.7.3.3.1
-- 1.3.6.1.4.1.6346.1.8.7.3.3.1
-- 1.3.6.1.4.1.6346.1.8.7.3.3.1
-- 1.3.6.1.4.1.6346.1.8.7.3.3.1
		-- 1.3.6.1.4.1.6346.1.8.7.3.3.1
		tpu1cTelemetryAnalogInputMinValueEntry OBJECT-TYPE
			SYNTAX Tpu1cTelemetryAnalogInputMinValueEntry
			MAX-ACCESS not-accessible
			STATUS current
			DESCRIPTION
				"Description."
			INDEX { tpu1cTelemetryAnalogInputMinValueIndex }
			::= { tpu1cTelemetryAnalogInputMinValueTable 1 }

		
		Tpu1cTelemetryAnalogInputMinValueEntry ::=
			SEQUENCE { 
				tpu1cTelemetryAnalogInputMinValueIndex
					Integer32,
				tpu1cTelemetryAnalogInputMinValue
					DataFloat
			 }

--       1.3.6.1.4.1.6346.1.8.7.3.3.1.1
-- 1.3.6.1.4.1.6346.1.8.7.3.3.1.1
-- 1.3.6.1.4.1.6346.1.8.7.3.3.1.1
-- 1.3.6.1.4.1.6346.1.8.7.3.3.1.1
-- 1.3.6.1.4.1.6346.1.8.7.3.3.1.1
-- 1.3.6.1.4.1.6346.1.8.7.3.3.1.1
		-- 1.3.6.1.4.1.6346.1.8.7.3.3.1.1
		tpu1cTelemetryAnalogInputMinValueIndex OBJECT-TYPE
			SYNTAX Integer32 (1..12)
			MAX-ACCESS not-accessible
			STATUS current
			DESCRIPTION
				"Description."
			::= { tpu1cTelemetryAnalogInputMinValueEntry 1 }

		
--       1.3.6.1.4.1.6346.1.8.7.3.3.1.2
-- 1.3.6.1.4.1.6346.1.8.7.3.3.1.2
-- 1.3.6.1.4.1.6346.1.8.7.3.3.1.2
-- 1.3.6.1.4.1.6346.1.8.7.3.3.1.2
-- 1.3.6.1.4.1.6346.1.8.7.3.3.1.2
-- 1.3.6.1.4.1.6346.1.8.7.3.3.1.2
		-- 1.3.6.1.4.1.6346.1.8.7.3.3.1.2
		tpu1cTelemetryAnalogInputMinValue OBJECT-TYPE
			SYNTAX DataFloat
			MAX-ACCESS read-only
			STATUS current
			DESCRIPTION
				"Description."
			::= { tpu1cTelemetryAnalogInputMinValueEntry 2 }

		
--       1.3.6.1.4.1.6346.1.8.7.3.4
-- 1.3.6.1.4.1.6346.1.8.7.3.4
-- 1.3.6.1.4.1.6346.1.8.7.3.4
-- 1.3.6.1.4.1.6346.1.8.7.3.4
-- 1.3.6.1.4.1.6346.1.8.7.3.4
-- 1.3.6.1.4.1.6346.1.8.7.3.4
		-- 1.3.6.1.4.1.6346.1.8.7.3.4
		tpu1cTelemetryAnalogInputMaxMinReset OBJECT-TYPE
			SYNTAX BITS
				{
				inp1(0),
				inp2(1),
				inp3(2),
				inp4(3),
				inp5(4),
				inp6(5),
				inp7(6),
				inp8(7),
				inp9(8),
				inp10(9),
				inp11(10),
				inp12(11)
				}
			MAX-ACCESS read-write
			STATUS current
			DESCRIPTION
				"Description."
			::= { tpu1cTelemetryAnalogInputs 4 }

		
--       1.3.6.1.4.1.6346.1.8.7.4
-- 1.3.6.1.4.1.6346.1.8.7.4
-- 1.3.6.1.4.1.6346.1.8.7.4
-- 1.3.6.1.4.1.6346.1.8.7.4
-- 1.3.6.1.4.1.6346.1.8.7.4
-- 1.3.6.1.4.1.6346.1.8.7.4
		-- 1.3.6.1.4.1.6346.1.8.7.4
		tpu1cTelemetryAnalogOutputs OBJECT IDENTIFIER ::= { tpu1cTelemetry 4 }

		
--       1.3.6.1.4.1.6346.1.8.7.4.1
-- 1.3.6.1.4.1.6346.1.8.7.4.1
-- 1.3.6.1.4.1.6346.1.8.7.4.1
-- 1.3.6.1.4.1.6346.1.8.7.4.1
-- 1.3.6.1.4.1.6346.1.8.7.4.1
-- 1.3.6.1.4.1.6346.1.8.7.4.1
		-- 1.3.6.1.4.1.6346.1.8.7.4.1
		tpu1cTelemetryAnalogOutputCurValueTable OBJECT-TYPE
			SYNTAX SEQUENCE OF Tpu1cTelemetryAnalogOutputCurValueEntry
			MAX-ACCESS not-accessible
			STATUS current
			DESCRIPTION
				"Description."
			::= { tpu1cTelemetryAnalogOutputs 1 }

		
--       1.3.6.1.4.1.6346.1.8.7.4.1.1
-- 1.3.6.1.4.1.6346.1.8.7.4.1.1
-- 1.3.6.1.4.1.6346.1.8.7.4.1.1
-- 1.3.6.1.4.1.6346.1.8.7.4.1.1
-- 1.3.6.1.4.1.6346.1.8.7.4.1.1
-- 1.3.6.1.4.1.6346.1.8.7.4.1.1
		-- 1.3.6.1.4.1.6346.1.8.7.4.1.1
		tpu1cTelemetryAnalogOutputCurValueEntry OBJECT-TYPE
			SYNTAX Tpu1cTelemetryAnalogOutputCurValueEntry
			MAX-ACCESS not-accessible
			STATUS current
			DESCRIPTION
				"Description."
			INDEX { tpu1cTelemetryAnalogOutputCurValueIndex }
			::= { tpu1cTelemetryAnalogOutputCurValueTable 1 }

		
		Tpu1cTelemetryAnalogOutputCurValueEntry ::=
			SEQUENCE { 
				tpu1cTelemetryAnalogOutputCurValueIndex
					Integer32,
				tpu1cTelemetryAnalogOutputCurValue
					DataFloat
			 }

--       1.3.6.1.4.1.6346.1.8.7.4.1.1.1
-- 1.3.6.1.4.1.6346.1.8.7.4.1.1.1
-- 1.3.6.1.4.1.6346.1.8.7.4.1.1.1
-- 1.3.6.1.4.1.6346.1.8.7.4.1.1.1
-- 1.3.6.1.4.1.6346.1.8.7.4.1.1.1
-- 1.3.6.1.4.1.6346.1.8.7.4.1.1.1
		-- 1.3.6.1.4.1.6346.1.8.7.4.1.1.1
		tpu1cTelemetryAnalogOutputCurValueIndex OBJECT-TYPE
			SYNTAX Integer32 (1..12)
			MAX-ACCESS not-accessible
			STATUS current
			DESCRIPTION
				"Description."
			::= { tpu1cTelemetryAnalogOutputCurValueEntry 1 }

		
--       1.3.6.1.4.1.6346.1.8.7.4.1.1.2
-- 1.3.6.1.4.1.6346.1.8.7.4.1.1.2
-- 1.3.6.1.4.1.6346.1.8.7.4.1.1.2
-- 1.3.6.1.4.1.6346.1.8.7.4.1.1.2
-- 1.3.6.1.4.1.6346.1.8.7.4.1.1.2
-- 1.3.6.1.4.1.6346.1.8.7.4.1.1.2
		-- 1.3.6.1.4.1.6346.1.8.7.4.1.1.2
		tpu1cTelemetryAnalogOutputCurValue OBJECT-TYPE
			SYNTAX DataFloat
			MAX-ACCESS read-only
			STATUS current
			DESCRIPTION
				"Description."
			::= { tpu1cTelemetryAnalogOutputCurValueEntry 2 }

		
--       1.3.6.1.4.1.6346.1.8.7.4.2
-- 1.3.6.1.4.1.6346.1.8.7.4.2
-- 1.3.6.1.4.1.6346.1.8.7.4.2
-- 1.3.6.1.4.1.6346.1.8.7.4.2
-- 1.3.6.1.4.1.6346.1.8.7.4.2
-- 1.3.6.1.4.1.6346.1.8.7.4.2
		-- 1.3.6.1.4.1.6346.1.8.7.4.2
		tpu1cTelemetryAnalogOutputMaxValueTable OBJECT-TYPE
			SYNTAX SEQUENCE OF Tpu1cTelemetryAnalogOutputMaxValueEntry
			MAX-ACCESS not-accessible
			STATUS current
			DESCRIPTION
				"Description."
			::= { tpu1cTelemetryAnalogOutputs 2 }

		
--       1.3.6.1.4.1.6346.1.8.7.4.2.1
-- 1.3.6.1.4.1.6346.1.8.7.4.2.1
-- 1.3.6.1.4.1.6346.1.8.7.4.2.1
-- 1.3.6.1.4.1.6346.1.8.7.4.2.1
-- 1.3.6.1.4.1.6346.1.8.7.4.2.1
-- 1.3.6.1.4.1.6346.1.8.7.4.2.1
		-- 1.3.6.1.4.1.6346.1.8.7.4.2.1
		tpu1cTelemetryAnalogOutputMaxValueEntry OBJECT-TYPE
			SYNTAX Tpu1cTelemetryAnalogOutputMaxValueEntry
			MAX-ACCESS not-accessible
			STATUS current
			DESCRIPTION
				"Description."
			INDEX { tpu1cTelemetryAnalogOutputMaxValueIndex }
			::= { tpu1cTelemetryAnalogOutputMaxValueTable 1 }

		
		Tpu1cTelemetryAnalogOutputMaxValueEntry ::=
			SEQUENCE { 
				tpu1cTelemetryAnalogOutputMaxValueIndex
					Integer32,
				tpu1cTelemetryAnalogOutputMaxValue
					DataFloat
			 }

--       1.3.6.1.4.1.6346.1.8.7.4.2.1.1
-- 1.3.6.1.4.1.6346.1.8.7.4.2.1.1
-- 1.3.6.1.4.1.6346.1.8.7.4.2.1.1
-- 1.3.6.1.4.1.6346.1.8.7.4.2.1.1
-- 1.3.6.1.4.1.6346.1.8.7.4.2.1.1
-- 1.3.6.1.4.1.6346.1.8.7.4.2.1.1
		-- 1.3.6.1.4.1.6346.1.8.7.4.2.1.1
		tpu1cTelemetryAnalogOutputMaxValueIndex OBJECT-TYPE
			SYNTAX Integer32 (1..12)
			MAX-ACCESS not-accessible
			STATUS current
			DESCRIPTION
				"Description."
			::= { tpu1cTelemetryAnalogOutputMaxValueEntry 1 }

		
--       1.3.6.1.4.1.6346.1.8.7.4.2.1.2
-- 1.3.6.1.4.1.6346.1.8.7.4.2.1.2
-- 1.3.6.1.4.1.6346.1.8.7.4.2.1.2
-- 1.3.6.1.4.1.6346.1.8.7.4.2.1.2
-- 1.3.6.1.4.1.6346.1.8.7.4.2.1.2
-- 1.3.6.1.4.1.6346.1.8.7.4.2.1.2
		-- 1.3.6.1.4.1.6346.1.8.7.4.2.1.2
		tpu1cTelemetryAnalogOutputMaxValue OBJECT-TYPE
			SYNTAX DataFloat
			MAX-ACCESS read-only
			STATUS current
			DESCRIPTION
				"Description."
			::= { tpu1cTelemetryAnalogOutputMaxValueEntry 2 }

		
--       1.3.6.1.4.1.6346.1.8.7.4.3
-- 1.3.6.1.4.1.6346.1.8.7.4.3
-- 1.3.6.1.4.1.6346.1.8.7.4.3
-- 1.3.6.1.4.1.6346.1.8.7.4.3
-- 1.3.6.1.4.1.6346.1.8.7.4.3
-- 1.3.6.1.4.1.6346.1.8.7.4.3
		-- 1.3.6.1.4.1.6346.1.8.7.4.3
		tpu1cTelemetryAnalogOutputMinValueTable OBJECT-TYPE
			SYNTAX SEQUENCE OF Tpu1cTelemetryAnalogOutputMinValueEntry
			MAX-ACCESS not-accessible
			STATUS current
			DESCRIPTION
				"Description."
			::= { tpu1cTelemetryAnalogOutputs 3 }

		
--       1.3.6.1.4.1.6346.1.8.7.4.3.1
-- 1.3.6.1.4.1.6346.1.8.7.4.3.1
-- 1.3.6.1.4.1.6346.1.8.7.4.3.1
-- 1.3.6.1.4.1.6346.1.8.7.4.3.1
-- 1.3.6.1.4.1.6346.1.8.7.4.3.1
-- 1.3.6.1.4.1.6346.1.8.7.4.3.1
		-- 1.3.6.1.4.1.6346.1.8.7.4.3.1
		tpu1cTelemetryAnalogOutputMinValueEntry OBJECT-TYPE
			SYNTAX Tpu1cTelemetryAnalogOutputMinValueEntry
			MAX-ACCESS not-accessible
			STATUS current
			DESCRIPTION
				"Description."
			INDEX { tpu1cTelemetryAnalogOutputMinValueIndex }
			::= { tpu1cTelemetryAnalogOutputMinValueTable 1 }

		
		Tpu1cTelemetryAnalogOutputMinValueEntry ::=
			SEQUENCE { 
				tpu1cTelemetryAnalogOutputMinValueIndex
					Integer32,
				tpu1cTelemetryAnalogOutputMinValue
					DataFloat
			 }

--       1.3.6.1.4.1.6346.1.8.7.4.3.1.1
-- 1.3.6.1.4.1.6346.1.8.7.4.3.1.1
-- 1.3.6.1.4.1.6346.1.8.7.4.3.1.1
-- 1.3.6.1.4.1.6346.1.8.7.4.3.1.1
-- 1.3.6.1.4.1.6346.1.8.7.4.3.1.1
-- 1.3.6.1.4.1.6346.1.8.7.4.3.1.1
		-- 1.3.6.1.4.1.6346.1.8.7.4.3.1.1
		tpu1cTelemetryAnalogOutputMinValueIndex OBJECT-TYPE
			SYNTAX Integer32 (1..12)
			MAX-ACCESS not-accessible
			STATUS current
			DESCRIPTION
				"Description."
			::= { tpu1cTelemetryAnalogOutputMinValueEntry 1 }

		
--       1.3.6.1.4.1.6346.1.8.7.4.3.1.2
-- 1.3.6.1.4.1.6346.1.8.7.4.3.1.2
-- 1.3.6.1.4.1.6346.1.8.7.4.3.1.2
-- 1.3.6.1.4.1.6346.1.8.7.4.3.1.2
-- 1.3.6.1.4.1.6346.1.8.7.4.3.1.2
-- 1.3.6.1.4.1.6346.1.8.7.4.3.1.2
		-- 1.3.6.1.4.1.6346.1.8.7.4.3.1.2
		tpu1cTelemetryAnalogOutputMinValue OBJECT-TYPE
			SYNTAX DataFloat
			MAX-ACCESS read-only
			STATUS current
			DESCRIPTION
				"Description."
			::= { tpu1cTelemetryAnalogOutputMinValueEntry 2 }

		
--       1.3.6.1.4.1.6346.1.8.7.4.4
-- 1.3.6.1.4.1.6346.1.8.7.4.4
-- 1.3.6.1.4.1.6346.1.8.7.4.4
-- 1.3.6.1.4.1.6346.1.8.7.4.4
-- 1.3.6.1.4.1.6346.1.8.7.4.4
-- 1.3.6.1.4.1.6346.1.8.7.4.4
		-- 1.3.6.1.4.1.6346.1.8.7.4.4
		tpu1cTelemetryAnalogOutputMaxMinReset OBJECT-TYPE
			SYNTAX BITS
				{
				out1(0),
				out2(1),
				out3(2),
				out4(3),
				out5(4),
				out6(5),
				out7(6),
				out8(7),
				out9(8),
				out10(9),
				out11(10),
				out12(11)
				}
			MAX-ACCESS read-write
			STATUS current
			DESCRIPTION
				"Description."
			::= { tpu1cTelemetryAnalogOutputs 4 }

		
--       1.3.6.1.4.1.6346.1.8.8
-- 1.3.6.1.4.1.6346.1.8.8
-- 1.3.6.1.4.1.6346.1.8.8
-- 1.3.6.1.4.1.6346.1.8.8
-- 1.3.6.1.4.1.6346.1.8.8
-- 1.3.6.1.4.1.6346.1.8.8
		-- 1.3.6.1.4.1.6346.1.8.8
		tpu1cChannelQuality OBJECT IDENTIFIER ::= { tpu1c 8 }

		
--       1.3.6.1.4.1.6346.1.8.8.1
-- 1.3.6.1.4.1.6346.1.8.8.1
-- 1.3.6.1.4.1.6346.1.8.8.1
-- 1.3.6.1.4.1.6346.1.8.8.1
-- 1.3.6.1.4.1.6346.1.8.8.1
-- 1.3.6.1.4.1.6346.1.8.8.1
		-- 1.3.6.1.4.1.6346.1.8.8.1
		tpu1cSignalNoiseRatioValueTable OBJECT-TYPE
			SYNTAX SEQUENCE OF Tpu1cSignalNoiseRatioValueEntry
			MAX-ACCESS not-accessible
			STATUS current
			DESCRIPTION
				"Description."
			::= { tpu1cChannelQuality 1 }

		
--       1.3.6.1.4.1.6346.1.8.8.1.1
-- 1.3.6.1.4.1.6346.1.8.8.1.1
-- 1.3.6.1.4.1.6346.1.8.8.1.1
-- 1.3.6.1.4.1.6346.1.8.8.1.1
-- 1.3.6.1.4.1.6346.1.8.8.1.1
-- 1.3.6.1.4.1.6346.1.8.8.1.1
		-- 1.3.6.1.4.1.6346.1.8.8.1.1
		tpu1cSignalNoiseRatioValueEntry OBJECT-TYPE
			SYNTAX Tpu1cSignalNoiseRatioValueEntry
			MAX-ACCESS not-accessible
			STATUS current
			DESCRIPTION
				"Description."
			INDEX { tpu1cSignalNoiseRatioValueIndex }
			::= { tpu1cSignalNoiseRatioValueTable 1 }

		
		Tpu1cSignalNoiseRatioValueEntry ::=
			SEQUENCE { 
				tpu1cSignalNoiseRatioValueIndex
					Integer32,
				tpu1cSignalNoiseRatioValue
					DataFloat
			 }

--       1.3.6.1.4.1.6346.1.8.8.1.1.1
-- 1.3.6.1.4.1.6346.1.8.8.1.1.1
-- 1.3.6.1.4.1.6346.1.8.8.1.1.1
-- 1.3.6.1.4.1.6346.1.8.8.1.1.1
-- 1.3.6.1.4.1.6346.1.8.8.1.1.1
-- 1.3.6.1.4.1.6346.1.8.8.1.1.1
		-- 1.3.6.1.4.1.6346.1.8.8.1.1.1
		tpu1cSignalNoiseRatioValueIndex OBJECT-TYPE
			SYNTAX Integer32 (1..2)
			MAX-ACCESS not-accessible
			STATUS current
			DESCRIPTION
				"Description."
			::= { tpu1cSignalNoiseRatioValueEntry 1 }

		
--       1.3.6.1.4.1.6346.1.8.8.1.1.2
-- 1.3.6.1.4.1.6346.1.8.8.1.1.2
-- 1.3.6.1.4.1.6346.1.8.8.1.1.2
-- 1.3.6.1.4.1.6346.1.8.8.1.1.2
-- 1.3.6.1.4.1.6346.1.8.8.1.1.2
-- 1.3.6.1.4.1.6346.1.8.8.1.1.2
		-- 1.3.6.1.4.1.6346.1.8.8.1.1.2
		tpu1cSignalNoiseRatioValue OBJECT-TYPE
			SYNTAX DataFloat
			MAX-ACCESS read-only
			STATUS current
			DESCRIPTION
				"Description."
			::= { tpu1cSignalNoiseRatioValueEntry 2 }

		
--       1.3.6.1.4.1.6346.1.8.8.2
-- 1.3.6.1.4.1.6346.1.8.8.2
-- 1.3.6.1.4.1.6346.1.8.8.2
-- 1.3.6.1.4.1.6346.1.8.8.2
-- 1.3.6.1.4.1.6346.1.8.8.2
-- 1.3.6.1.4.1.6346.1.8.8.2
		-- 1.3.6.1.4.1.6346.1.8.8.2
		tpu1cBitErrorRateValueTable OBJECT-TYPE
			SYNTAX SEQUENCE OF Tpu1cBitErrorRateValueEntry
			MAX-ACCESS not-accessible
			STATUS current
			DESCRIPTION
				"Description."
			::= { tpu1cChannelQuality 2 }

		
--       1.3.6.1.4.1.6346.1.8.8.2.1
-- 1.3.6.1.4.1.6346.1.8.8.2.1
-- 1.3.6.1.4.1.6346.1.8.8.2.1
-- 1.3.6.1.4.1.6346.1.8.8.2.1
-- 1.3.6.1.4.1.6346.1.8.8.2.1
-- 1.3.6.1.4.1.6346.1.8.8.2.1
		-- 1.3.6.1.4.1.6346.1.8.8.2.1
		tpu1cBitErrorRateValueEntry OBJECT-TYPE
			SYNTAX Tpu1cBitErrorRateValueEntry
			MAX-ACCESS not-accessible
			STATUS current
			DESCRIPTION
				"Description."
			INDEX { tpu1cBitErrorRateValueIndex }
			::= { tpu1cBitErrorRateValueTable 1 }

		
		Tpu1cBitErrorRateValueEntry ::=
			SEQUENCE { 
				tpu1cBitErrorRateValueIndex
					Integer32,
				tpu1cBitErrorRateValue
					DataFloat
			 }

--       1.3.6.1.4.1.6346.1.8.8.2.1.1
-- 1.3.6.1.4.1.6346.1.8.8.2.1.1
-- 1.3.6.1.4.1.6346.1.8.8.2.1.1
-- 1.3.6.1.4.1.6346.1.8.8.2.1.1
-- 1.3.6.1.4.1.6346.1.8.8.2.1.1
-- 1.3.6.1.4.1.6346.1.8.8.2.1.1
		-- 1.3.6.1.4.1.6346.1.8.8.2.1.1
		tpu1cBitErrorRateValueIndex OBJECT-TYPE
			SYNTAX Integer32 (1..2)
			MAX-ACCESS not-accessible
			STATUS current
			DESCRIPTION
				"Description."
			::= { tpu1cBitErrorRateValueEntry 1 }

		
--       1.3.6.1.4.1.6346.1.8.8.2.1.2
-- 1.3.6.1.4.1.6346.1.8.8.2.1.2
-- 1.3.6.1.4.1.6346.1.8.8.2.1.2
-- 1.3.6.1.4.1.6346.1.8.8.2.1.2
-- 1.3.6.1.4.1.6346.1.8.8.2.1.2
-- 1.3.6.1.4.1.6346.1.8.8.2.1.2
		-- 1.3.6.1.4.1.6346.1.8.8.2.1.2
		tpu1cBitErrorRateValue OBJECT-TYPE
			SYNTAX DataFloat
			MAX-ACCESS read-only
			STATUS current
			DESCRIPTION
				"Description."
			::= { tpu1cBitErrorRateValueEntry 2 }

		
--       1.3.6.1.4.1.6346.1.8.9
-- 1.3.6.1.4.1.6346.1.8.9
-- 1.3.6.1.4.1.6346.1.8.9
-- 1.3.6.1.4.1.6346.1.8.9
-- 1.3.6.1.4.1.6346.1.8.9
-- 1.3.6.1.4.1.6346.1.8.9
		-- 1.3.6.1.4.1.6346.1.8.9
		tpu1cAlarms OBJECT IDENTIFIER ::= { tpu1c 9 }

		
--       1.3.6.1.4.1.6346.1.8.9.1
-- 1.3.6.1.4.1.6346.1.8.9.1
-- 1.3.6.1.4.1.6346.1.8.9.1
-- 1.3.6.1.4.1.6346.1.8.9.1
-- 1.3.6.1.4.1.6346.1.8.9.1
-- 1.3.6.1.4.1.6346.1.8.9.1
		-- 1.3.6.1.4.1.6346.1.8.9.1
		tpu1cSystemAlarmStatus OBJECT-TYPE
			SYNTAX BITS
				{
				rtcExternalSyncLost(0),
				ethLink61850Error(1),
				powerSupply1Fail(2),
				powerSupply2Fail(3),
				teleMetryError(4),
				generalRemoteAlarmTP1(5),
				generalRemoteAlarmTP2(6),
				eth2Link61850Error(7),
				tpDisabledMhS(8),
				bit9(9),
				bit10(10),
				bit11(11),
				bit12(12),
				bit13(13),
				bit14(14),
				bit15(15),
				bit16(16),
				bit17(17),
				bit18(18),
				bit19(19),
				bit20(20),
				moduleMainError(21),
				moduleSlot0Error(22),
				moduleSlot1Error(23),
				moduleSlot2Error(24),
				moduleSlot3Error(25),
				moduleSlot4Error(26),
				moduleSlot5Error(27),
				moduleSlot6Error(28),
				moduleSlot7Error(29),
				moduleSlot8Error(30),
				moduleSlot9Error(31)
				}
			MAX-ACCESS read-write
			STATUS current
			DESCRIPTION
				"Description."
			::= { tpu1cAlarms 1 }

		
--       1.3.6.1.4.1.6346.1.8.9.2
-- 1.3.6.1.4.1.6346.1.8.9.2
-- 1.3.6.1.4.1.6346.1.8.9.2
-- 1.3.6.1.4.1.6346.1.8.9.2
-- 1.3.6.1.4.1.6346.1.8.9.2
-- 1.3.6.1.4.1.6346.1.8.9.2
		-- 1.3.6.1.4.1.6346.1.8.9.2
		tpu1cChannelAlarmStatusTable OBJECT-TYPE
			SYNTAX SEQUENCE OF Tpu1cChannelAlarmStatusEntry
			MAX-ACCESS not-accessible
			STATUS current
			DESCRIPTION
				"Description."
			::= { tpu1cAlarms 2 }

		
--       1.3.6.1.4.1.6346.1.8.9.2.1
-- 1.3.6.1.4.1.6346.1.8.9.2.1
-- 1.3.6.1.4.1.6346.1.8.9.2.1
-- 1.3.6.1.4.1.6346.1.8.9.2.1
-- 1.3.6.1.4.1.6346.1.8.9.2.1
-- 1.3.6.1.4.1.6346.1.8.9.2.1
		-- 1.3.6.1.4.1.6346.1.8.9.2.1
		tpu1cChannelAlarmStatusEntry OBJECT-TYPE
			SYNTAX Tpu1cChannelAlarmStatusEntry
			MAX-ACCESS not-accessible
			STATUS current
			DESCRIPTION
				"Description."
			INDEX { tpu1cChannelAlarmStatusIndex }
			::= { tpu1cChannelAlarmStatusTable 1 }

		
		Tpu1cChannelAlarmStatusEntry ::=
			SEQUENCE { 
				tpu1cChannelAlarmStatusIndex
					Integer32,
				tpu1cChannelAlarmStatus
					BITS
			 }

--       1.3.6.1.4.1.6346.1.8.9.2.1.1
-- 1.3.6.1.4.1.6346.1.8.9.2.1.1
-- 1.3.6.1.4.1.6346.1.8.9.2.1.1
-- 1.3.6.1.4.1.6346.1.8.9.2.1.1
-- 1.3.6.1.4.1.6346.1.8.9.2.1.1
-- 1.3.6.1.4.1.6346.1.8.9.2.1.1
		-- 1.3.6.1.4.1.6346.1.8.9.2.1.1
		tpu1cChannelAlarmStatusIndex OBJECT-TYPE
			SYNTAX Integer32 (1..2)
			MAX-ACCESS not-accessible
			STATUS current
			DESCRIPTION
				"Description."
			::= { tpu1cChannelAlarmStatusEntry 1 }

		
--       1.3.6.1.4.1.6346.1.8.9.2.1.2
-- 1.3.6.1.4.1.6346.1.8.9.2.1.2
-- 1.3.6.1.4.1.6346.1.8.9.2.1.2
-- 1.3.6.1.4.1.6346.1.8.9.2.1.2
-- 1.3.6.1.4.1.6346.1.8.9.2.1.2
-- 1.3.6.1.4.1.6346.1.8.9.2.1.2
		-- 1.3.6.1.4.1.6346.1.8.9.2.1.2
		tpu1cChannelAlarmStatus OBJECT-TYPE
			SYNTAX BITS
				{
				manualBlocking(0),
				lineTestError(1),
				identifyCodeError(2),
				securityCodeError(3),
				syncLoss(4),
				signalLossDigitalIOTU(5),
				bitErrorRateHigh(6),
				remoteAlarmIndicationIOCT(7),
				c3794AIS(8),
				receiverBlocked(9),
				signalLoss(10),
				guardLevelLow(11),
				guardLevelExcess(12),
				signalNoiseRatioLow(13),
				receiverError(14),
				ipMeanTransferDelay(15),
				ipFrameDelayVariation(16),
				ipFrameLossRatio(17),
				ipLinkDown(18),
				ipSyncLoss(19),
				c3794LOS(20),
				c3794PathYellow(21),
				sfp1TemperatureAlarm(22),
				sfp1VccAlarm(23),
				sfp1BiasAlarm(24),
				sfp1TxPowerAlarm(25),
				sfp1RxPowerAlarm(26),
				sfp1TemperatureWarning(27),
				sfp1VccWarning(28),
				sfp1BiasWarning(29),
				sfp1TxPowerWarning(30),
				sfp1RxPowerWarning(31)
				}
			MAX-ACCESS read-only
			STATUS current
			DESCRIPTION
				"Description."
			::= { tpu1cChannelAlarmStatusEntry 2 }

		
--       1.3.6.1.4.1.6346.1.8.9.3
-- 1.3.6.1.4.1.6346.1.8.9.3
-- 1.3.6.1.4.1.6346.1.8.9.3
-- 1.3.6.1.4.1.6346.1.8.9.3
-- 1.3.6.1.4.1.6346.1.8.9.3
-- 1.3.6.1.4.1.6346.1.8.9.3
		-- 1.3.6.1.4.1.6346.1.8.9.3
		tpu1cIeptAlarmStatus OBJECT-TYPE
			SYNTAX BITS
				{
				iept61850LinkDown(0),
				toutInputIEC61850Command1(1),
				toutInputIEC61850Command2(2),
				toutInputIEC61850Command3(3),
				toutInputIEC61850Command4(4),
				toutInputIEC61850Command5(5),
				toutInputIEC61850Command6(6),
				toutInputIEC61850Command7(7),
				toutInputIEC61850Command8(8),
				toutInputIEC61850Command9(9),
				toutInputIEC61850Command10(10),
				toutInputIEC61850Command11(11),
				toutInputIEC61850Command12(12),
				toutInputIEC61850Command13(13),
				toutInputIEC61850Command14(14),
				toutInputIEC61850Command15(15),
				toutInputIEC61850Command16(16),
				outputIEC61850Command(17),
				systemClockFail(18)
				}
			MAX-ACCESS read-only
			STATUS current
			DESCRIPTION
				"Description."
			::= { tpu1cAlarms 3 }

		
--       1.3.6.1.4.1.6346.1.8.9.4
-- 1.3.6.1.4.1.6346.1.8.9.4
-- 1.3.6.1.4.1.6346.1.8.9.4
-- 1.3.6.1.4.1.6346.1.8.9.4
-- 1.3.6.1.4.1.6346.1.8.9.4
-- 1.3.6.1.4.1.6346.1.8.9.4
		-- 1.3.6.1.4.1.6346.1.8.9.4
		tpu1cChannelAlarmStatusHighTable OBJECT-TYPE
			SYNTAX SEQUENCE OF Tpu1cChannelAlarmStatusHighEntry
			MAX-ACCESS not-accessible
			STATUS current
			DESCRIPTION
				"Description."
			::= { tpu1cAlarms 4 }

		
--       1.3.6.1.4.1.6346.1.8.9.4.1
-- 1.3.6.1.4.1.6346.1.8.9.4.1
-- 1.3.6.1.4.1.6346.1.8.9.4.1
-- 1.3.6.1.4.1.6346.1.8.9.4.1
-- 1.3.6.1.4.1.6346.1.8.9.4.1
-- 1.3.6.1.4.1.6346.1.8.9.4.1
		-- 1.3.6.1.4.1.6346.1.8.9.4.1
		tpu1cChannelAlarmStatusHighEntry OBJECT-TYPE
			SYNTAX Tpu1cChannelAlarmStatusHighEntry
			MAX-ACCESS not-accessible
			STATUS current
			DESCRIPTION
				"Description."
			INDEX { tpu1cChannelAlarmStatusHighIndex }
			::= { tpu1cChannelAlarmStatusHighTable 1 }

		
		Tpu1cChannelAlarmStatusHighEntry ::=
			SEQUENCE { 
				tpu1cChannelAlarmStatusHighIndex
					Integer32,
				tpu1cChannelAlarmStatusHigh
					BITS
			 }

--       1.3.6.1.4.1.6346.1.8.9.4.1.1
-- 1.3.6.1.4.1.6346.1.8.9.4.1.1
-- 1.3.6.1.4.1.6346.1.8.9.4.1.1
-- 1.3.6.1.4.1.6346.1.8.9.4.1.1
-- 1.3.6.1.4.1.6346.1.8.9.4.1.1
-- 1.3.6.1.4.1.6346.1.8.9.4.1.1
		-- 1.3.6.1.4.1.6346.1.8.9.4.1.1
		tpu1cChannelAlarmStatusHighIndex OBJECT-TYPE
			SYNTAX Integer32 (1..2)
			MAX-ACCESS not-accessible
			STATUS current
			DESCRIPTION
				"Description."
			::= { tpu1cChannelAlarmStatusHighEntry 1 }

		
--       1.3.6.1.4.1.6346.1.8.9.4.1.2
-- 1.3.6.1.4.1.6346.1.8.9.4.1.2
-- 1.3.6.1.4.1.6346.1.8.9.4.1.2
-- 1.3.6.1.4.1.6346.1.8.9.4.1.2
-- 1.3.6.1.4.1.6346.1.8.9.4.1.2
-- 1.3.6.1.4.1.6346.1.8.9.4.1.2
		-- 1.3.6.1.4.1.6346.1.8.9.4.1.2
		tpu1cChannelAlarmStatusHigh OBJECT-TYPE
			SYNTAX BITS
				{
				sfp1NotDetected(0),
				ipTxTrans(1),
				invCmdRx(2),
				sfp2TempAlarm(3),
				sfp2VccAlarm(4),
				sfp2BiasAlarm(5),
				sfp2TxPowerAlarm(6),
				sfp2RxPowerAlarm(7),
				sfp2TempWarn(8),
				sfp2VccWarn(9),
				sfp2BiasWarn(10),
				sfp2TxPowerWarn(11),
				sfp2RxPowerWarn(12),
				sfp2NotPresent(13)
				}
			MAX-ACCESS read-only
			STATUS current
			DESCRIPTION
				"Description."
			::= { tpu1cChannelAlarmStatusHighEntry 2 }

		
--       1.3.6.1.4.1.6346.1.8.10
-- 1.3.6.1.4.1.6346.1.8.10
-- 1.3.6.1.4.1.6346.1.8.10
-- 1.3.6.1.4.1.6346.1.8.10
-- 1.3.6.1.4.1.6346.1.8.10
-- 1.3.6.1.4.1.6346.1.8.10
		-- 1.3.6.1.4.1.6346.1.8.10
		tpu1cEvents OBJECT IDENTIFIER ::= { tpu1c 10 }

		
--       1.3.6.1.4.1.6346.1.8.10.1
-- 1.3.6.1.4.1.6346.1.8.10.1
-- 1.3.6.1.4.1.6346.1.8.10.1
-- 1.3.6.1.4.1.6346.1.8.10.1
-- 1.3.6.1.4.1.6346.1.8.10.1
-- 1.3.6.1.4.1.6346.1.8.10.1
		-- 1.3.6.1.4.1.6346.1.8.10.1
		tpu1cSystemEventsStatus OBJECT-TYPE
			SYNTAX BITS
				{
				systemInit(0),
				bit1(1),
				bit2(2),
				bit3(3),
				bit4(4),
				bit5(5),
				bit6(6),
				bit7(7),
				bit8(8),
				bit9(9),
				bit10(10),
				bit11(11),
				bit12(12),
				bit13(13),
				bit14(14),
				bit15(15),
				bit16(16),
				bit17(17),
				bit18(18),
				bit19(19),
				bit20(20),
				bit21(21),
				bit22(22),
				bit23(23),
				bit24(24),
				bit25(25),
				bit26(26),
				bit27(27),
				bit28(28),
				bit29(29),
				bit30(30),
				bit31(31)
				}
			MAX-ACCESS read-only
			STATUS current
			DESCRIPTION
				"Description."
			::= { tpu1cEvents 1 }

		
--       1.3.6.1.4.1.6346.1.8.11
-- 1.3.6.1.4.1.6346.1.8.11
-- 1.3.6.1.4.1.6346.1.8.11
-- 1.3.6.1.4.1.6346.1.8.11
-- 1.3.6.1.4.1.6346.1.8.11
-- 1.3.6.1.4.1.6346.1.8.11
		-- 1.3.6.1.4.1.6346.1.8.11
		tpu1cSystemReset OBJECT IDENTIFIER ::= { tpu1c 11 }

		
--       1.3.6.1.4.1.6346.1.8.11.1
-- 1.3.6.1.4.1.6346.1.8.11.1
-- 1.3.6.1.4.1.6346.1.8.11.1
-- 1.3.6.1.4.1.6346.1.8.11.1
-- 1.3.6.1.4.1.6346.1.8.11.1
-- 1.3.6.1.4.1.6346.1.8.11.1
		-- 1.3.6.1.4.1.6346.1.8.11.1
		tpu1cSystemResetAction OBJECT-TYPE
			SYNTAX DataAction (0..1)
			MAX-ACCESS read-write
			STATUS current
			DESCRIPTION
				"Description."
			::= { tpu1cSystemReset 1 }

		
--       1.3.6.1.4.1.6346.1.8.12
-- 1.3.6.1.4.1.6346.1.8.12
-- 1.3.6.1.4.1.6346.1.8.12
-- 1.3.6.1.4.1.6346.1.8.12
-- 1.3.6.1.4.1.6346.1.8.12
-- 1.3.6.1.4.1.6346.1.8.12
		-- 1.3.6.1.4.1.6346.1.8.12
		tpu1cNotifications OBJECT IDENTIFIER ::= { tpu1c 12 }

		
--       1.3.6.1.4.1.6346.1.8.12.1
-- 1.3.6.1.4.1.6346.1.8.12.1
-- 1.3.6.1.4.1.6346.1.8.12.1
-- 1.3.6.1.4.1.6346.1.8.12.1
-- 1.3.6.1.4.1.6346.1.8.12.1
-- 1.3.6.1.4.1.6346.1.8.12.1
		-- 1.3.6.1.4.1.6346.1.8.12.1
		tpu1cNotificationEnable OBJECT IDENTIFIER ::= { tpu1cNotifications 1 }

		
--       1.3.6.1.4.1.6346.1.8.12.1.1
-- 1.3.6.1.4.1.6346.1.8.12.1.1
-- 1.3.6.1.4.1.6346.1.8.12.1.1
-- 1.3.6.1.4.1.6346.1.8.12.1.1
-- 1.3.6.1.4.1.6346.1.8.12.1.1
-- 1.3.6.1.4.1.6346.1.8.12.1.1
		-- 1.3.6.1.4.1.6346.1.8.12.1.1
		tpu1cNotificationEnableMask OBJECT-TYPE
			SYNTAX BITS
				{
				systemInit(0),
				rtcExternalSyncLost(1),
				ethLink61850Error(2),
				powerSupplyFail(3),
				teleMetryError(4),
				moduleError(5),
				manualRelayRelease(6),
				commandTx(7),
				commandRx(8),
				inputCircuitActivation(9),
				outputCircuitActivation(10),
				teleMetryInputActivation(11),
				teleMetryOutputActivation(12),
				manualBlocking(13),
				lineTestError(14),
				identifyCodeError(15),
				securityCodeError(16),
				syncLoss(17),
				bitErrorRateHigh(18),
				reserved(19),
				receiverBlocked(20),
				signalLoss(21),
				guardLevelLow(22),
				guardLevelExcess(23),
				signalNoiseRatioLow(24),
				receiverError(25),
				ipMeanTransferDelay(26),
				ipCellDelayVariation(27),
				ipCellLossRatio(28),
				ipLinkDown(29),
				ipSyncLoss(30),
				ieptToutInputIEC61850Command1(31)
				}
			MAX-ACCESS read-write
			STATUS current
			DESCRIPTION
				"Description."
			::= { tpu1cNotificationEnable 1 }

		
--       1.3.6.1.4.1.6346.1.8.12.1.2
-- 1.3.6.1.4.1.6346.1.8.12.1.2
-- 1.3.6.1.4.1.6346.1.8.12.1.2
-- 1.3.6.1.4.1.6346.1.8.12.1.2
-- 1.3.6.1.4.1.6346.1.8.12.1.2
-- 1.3.6.1.4.1.6346.1.8.12.1.2
		-- 1.3.6.1.4.1.6346.1.8.12.1.2
		tpu1cNotificationEnableMask2 OBJECT-TYPE
			SYNTAX BITS
				{
				ieptToutInputIEC61850Command2(0),
				ieptToutInputIEC61850Command3(1),
				ieptToutInputIEC61850Command4(2),
				ieptToutInputIEC61850Command5(3),
				ieptToutInputIEC61850Command6(4),
				ieptToutInputIEC61850Command7(5),
				ieptToutInputIEC61850Command8(6),
				ieptToutInputIEC61850Command9(7),
				ieptToutInputIEC61850Command10(8),
				ieptToutInputIEC61850Command11(9),
				ieptToutInputIEC61850Command12(10),
				ieptToutInputIEC61850Command13(11),
				ieptToutInputIEC61850Command14(12),
				ieptToutInputIEC61850Command15(13),
				ieptToutInputIEC61850Command16(14),
				ieptOutputIEC61850Command(15),
				ieptSystemClockFail(16),
				generalRemoteAlarm(17),
				c3794AIS(18),
				c3794LOS(19),
				c3794PathYellow(20),
				remoteAlarmIndicationIOCT(21),
				sfp1TemperatureAlarm(22),
				sfp1VccAlarm(23),
				sfp1BiasAlarm(24),
				sfp1TxPowerAlarm(25),
				sfp1RxPowerAlarm(26),
				sfp1TemperatureWarning(27),
				sfp1VccWarning(28),
				sfp1BiasWarning(29),
				sfp1TxPowerWarning(30),
				sfp1RxPowerWarning(31)
				}
			MAX-ACCESS read-write
			STATUS current
			DESCRIPTION
				"Description."
			::= { tpu1cNotificationEnable 2 }

		
--      1.3.6.1.4.1.6346.1.8.12.1.3
-- 1.3.6.1.4.1.6346.1.8.12.1.3
-- 1.3.6.1.4.1.6346.1.8.12.1.3
-- 1.3.6.1.4.1.6346.1.8.12.1.3
-- 1.3.6.1.4.1.6346.1.8.12.1.3
		-- 1.3.6.1.4.1.6346.1.8.12.1.3
		tpu1cNotificationEnableMask3 OBJECT-TYPE
			SYNTAX BITS { sfp1NotDetected(0) }
			MAX-ACCESS read-write
			STATUS current
			DESCRIPTION
				"Description."
			::= { tpu1cNotificationEnable 3 }

		
--       1.3.6.1.4.1.6346.1.8.12.2
-- 1.3.6.1.4.1.6346.1.8.12.2
-- 1.3.6.1.4.1.6346.1.8.12.2
-- 1.3.6.1.4.1.6346.1.8.12.2
-- 1.3.6.1.4.1.6346.1.8.12.2
-- 1.3.6.1.4.1.6346.1.8.12.2
		-- 1.3.6.1.4.1.6346.1.8.12.2
		tpu1cNotificationAuxData OBJECT IDENTIFIER ::= { tpu1cNotifications 2 }

		
--       1.3.6.1.4.1.6346.1.8.12.2.1
-- 1.3.6.1.4.1.6346.1.8.12.2.1
-- 1.3.6.1.4.1.6346.1.8.12.2.1
-- 1.3.6.1.4.1.6346.1.8.12.2.1
-- 1.3.6.1.4.1.6346.1.8.12.2.1
-- 1.3.6.1.4.1.6346.1.8.12.2.1
		-- 1.3.6.1.4.1.6346.1.8.12.2.1
		tpu1cNotifyCmdNum OBJECT-TYPE
			SYNTAX Integer32 (1..32)
			MAX-ACCESS read-only
			STATUS current
			DESCRIPTION
				"Description."
			::= { tpu1cNotificationAuxData 1 }

		
--       1.3.6.1.4.1.6346.1.8.12.2.2
-- 1.3.6.1.4.1.6346.1.8.12.2.2
-- 1.3.6.1.4.1.6346.1.8.12.2.2
-- 1.3.6.1.4.1.6346.1.8.12.2.2
-- 1.3.6.1.4.1.6346.1.8.12.2.2
-- 1.3.6.1.4.1.6346.1.8.12.2.2
		-- 1.3.6.1.4.1.6346.1.8.12.2.2
		tpu1cNotifyIONum OBJECT-TYPE
			SYNTAX Integer32 (1..32)
			MAX-ACCESS read-only
			STATUS current
			DESCRIPTION
				"Description."
			::= { tpu1cNotificationAuxData 2 }

		
--       1.3.6.1.4.1.6346.1.8.12.2.3
-- 1.3.6.1.4.1.6346.1.8.12.2.3
-- 1.3.6.1.4.1.6346.1.8.12.2.3
-- 1.3.6.1.4.1.6346.1.8.12.2.3
-- 1.3.6.1.4.1.6346.1.8.12.2.3
-- 1.3.6.1.4.1.6346.1.8.12.2.3
		-- 1.3.6.1.4.1.6346.1.8.12.2.3
		tpu1cNotifyChannel OBJECT-TYPE
			SYNTAX Integer32 (1..2)
			MAX-ACCESS read-only
			STATUS current
			DESCRIPTION
				"Description."
			::= { tpu1cNotificationAuxData 3 }

		
--       1.3.6.1.4.1.6346.1.8.12.2.4
-- 1.3.6.1.4.1.6346.1.8.12.2.4
-- 1.3.6.1.4.1.6346.1.8.12.2.4
-- 1.3.6.1.4.1.6346.1.8.12.2.4
-- 1.3.6.1.4.1.6346.1.8.12.2.4
-- 1.3.6.1.4.1.6346.1.8.12.2.4
		-- 1.3.6.1.4.1.6346.1.8.12.2.4
		tpu1cNotifyState OBJECT-TYPE
			SYNTAX Integer32
			MAX-ACCESS read-only
			STATUS current
			DESCRIPTION
				"Description."
			::= { tpu1cNotificationAuxData 4 }

		
--       1.3.6.1.4.1.6346.1.8.12.2.5
-- 1.3.6.1.4.1.6346.1.8.12.2.5
-- 1.3.6.1.4.1.6346.1.8.12.2.5
-- 1.3.6.1.4.1.6346.1.8.12.2.5
-- 1.3.6.1.4.1.6346.1.8.12.2.5
-- 1.3.6.1.4.1.6346.1.8.12.2.5
		-- 1.3.6.1.4.1.6346.1.8.12.2.5
		tpu1cNotifyTimeSecsUtc OBJECT-TYPE
			SYNTAX Unsigned32
			UNITS "seconds"
			MAX-ACCESS read-only
			STATUS current
			DESCRIPTION
				"Description."
			::= { tpu1cNotificationAuxData 5 }

		
--       1.3.6.1.4.1.6346.1.8.12.2.6
-- 1.3.6.1.4.1.6346.1.8.12.2.6
-- 1.3.6.1.4.1.6346.1.8.12.2.6
-- 1.3.6.1.4.1.6346.1.8.12.2.6
-- 1.3.6.1.4.1.6346.1.8.12.2.6
-- 1.3.6.1.4.1.6346.1.8.12.2.6
		-- 1.3.6.1.4.1.6346.1.8.12.2.6
		tpu1cNotifyTimeMillisecs OBJECT-TYPE
			SYNTAX Unsigned32
			UNITS "milliseconds"
			MAX-ACCESS read-only
			STATUS current
			DESCRIPTION
				"Description."
			::= { tpu1cNotificationAuxData 6 }

		
--       1.3.6.1.4.1.6346.1.8.12.2.7
-- 1.3.6.1.4.1.6346.1.8.12.2.7
-- 1.3.6.1.4.1.6346.1.8.12.2.7
-- 1.3.6.1.4.1.6346.1.8.12.2.7
-- 1.3.6.1.4.1.6346.1.8.12.2.7
-- 1.3.6.1.4.1.6346.1.8.12.2.7
		-- 1.3.6.1.4.1.6346.1.8.12.2.7
		tpu1cNotifySystemAlarmStatus OBJECT-TYPE
			SYNTAX BITS
				{
				rtcExternalSyncLost(0),
				ethLink61850Error(1),
				powerSupply1Fail(2),
				powerSupply2Fail(3),
				teleMetryError(4),
				generalRemoteAlarmTP1(5),
				generalRemoteAlarmTP2(6),
				bit7(7),
				bit8(8),
				bit9(9),
				bit10(10),
				bit11(11),
				bit12(12),
				bit13(13),
				bit14(14),
				bit15(15),
				bit16(16),
				bit17(17),
				bit18(18),
				bit19(19),
				bit20(20),
				moduleMainError(21),
				moduleSlot0Error(22),
				moduleSlot1Error(23),
				moduleSlot2Error(24),
				moduleSlot3Error(25),
				moduleSlot4Error(26),
				moduleSlot5Error(27),
				moduleSlot6Error(28),
				moduleSlot7Error(29),
				moduleSlot8Error(30),
				moduleSlot9Error(31)
				}
			MAX-ACCESS read-write
			STATUS current
			DESCRIPTION
				"Description."
			::= { tpu1cNotificationAuxData 7 }

		
--       1.3.6.1.4.1.6346.1.8.12.2.8
-- 1.3.6.1.4.1.6346.1.8.12.2.8
-- 1.3.6.1.4.1.6346.1.8.12.2.8
-- 1.3.6.1.4.1.6346.1.8.12.2.8
-- 1.3.6.1.4.1.6346.1.8.12.2.8
-- 1.3.6.1.4.1.6346.1.8.12.2.8
		-- 1.3.6.1.4.1.6346.1.8.12.2.8
		tpu1cNotifyChannelAlarmStatus OBJECT-TYPE
			SYNTAX BITS
				{
				manualBlocking(0),
				lineTestError(1),
				identifyCodeError(2),
				securityCodeError(3),
				syncLoss(4),
				signalLossDigitalIOTU(5),
				bitErrorRateHigh(6),
				remoteAlarmIndicationIOCT(7),
				c3794AIS(8),
				receiverBlocked(9),
				signalLoss(10),
				guardLevelLow(11),
				guardLevelExcess(12),
				signalNoiseRatioLow(13),
				receiverError(14),
				ipMeanTransferDelay(15),
				ipFrameDelayVariation(16),
				ipFrameLossRatio(17),
				ipLinkDown(18),
				ipSyncLoss(19),
				c3794LOS(20),
				c3794PathYellow(21),
				sfp1TemperatureAlarm(22),
				sfp1VccAlarm(23),
				sfp1BiasAlarm(24),
				sfp1TxPowerAlarm(25),
				sfp1RxPowerAlarm(26),
				sfp1TemperatureWarning(27),
				sfp1VccWarning(28),
				sfp1BiasWarning(29),
				sfp1TxPowerWarning(30),
				sfp1RxPowerWarning(31)
				}
			MAX-ACCESS read-only
			STATUS current
			DESCRIPTION
				"Description."
			::= { tpu1cNotificationAuxData 8 }

		
--       1.3.6.1.4.1.6346.1.8.12.2.9
-- 1.3.6.1.4.1.6346.1.8.12.2.9
-- 1.3.6.1.4.1.6346.1.8.12.2.9
-- 1.3.6.1.4.1.6346.1.8.12.2.9
-- 1.3.6.1.4.1.6346.1.8.12.2.9
-- 1.3.6.1.4.1.6346.1.8.12.2.9
		-- 1.3.6.1.4.1.6346.1.8.12.2.9
		tpu1cNotifyCmdCurrentState OBJECT-TYPE
			SYNTAX BITS
				{
				cmd1(0),
				cmd2(1),
				cmd3(2),
				cmd4(3),
				cmd5(4),
				cmd6(5),
				cmd7(6),
				cmd8(7),
				cmd9(8),
				cmd10(9),
				cmd11(10),
				cmd12(11),
				cmd13(12),
				cmd14(13),
				cmd15(14),
				cmd16(15),
				cmd17(16),
				cmd18(17),
				cmd19(18),
				cmd20(19),
				cmd21(20),
				cmd22(21),
				cmd23(22),
				cmd24(23),
				cmd25(24),
				cmd26(25),
				cmd27(26),
				cmd28(27),
				cmd29(28),
				cmd30(29),
				cmd31(30),
				cmd32(31)
				}
			MAX-ACCESS read-only
			STATUS current
			DESCRIPTION
				"Description."
			::= { tpu1cNotificationAuxData 9 }

		
--       1.3.6.1.4.1.6346.1.8.12.2.10
-- 1.3.6.1.4.1.6346.1.8.12.2.10
-- 1.3.6.1.4.1.6346.1.8.12.2.10
-- 1.3.6.1.4.1.6346.1.8.12.2.10
-- 1.3.6.1.4.1.6346.1.8.12.2.10
-- 1.3.6.1.4.1.6346.1.8.12.2.10
		-- 1.3.6.1.4.1.6346.1.8.12.2.10
		tpu1cNotifyInputCurrentState OBJECT-TYPE
			SYNTAX BITS
				{
				inp1(0),
				inp2(1),
				inp3(2),
				inp4(3),
				inp5(4),
				inp6(5),
				inp7(6),
				inp8(7),
				inp9(8),
				inp10(9),
				inp11(10),
				inp12(11),
				inp13(12),
				inp14(13),
				inp15(14),
				inp16(15),
				inp17(16),
				inp18(17),
				inp19(18),
				inp20(19),
				inp21(20),
				inp22(21),
				inp23(22),
				inp24(23),
				inp25(24),
				inp26(25),
				inp27(26),
				inp28(27),
				inp29(28),
				inp30(29),
				inp31(30),
				inp32(31)
				}
			MAX-ACCESS read-only
			STATUS current
			DESCRIPTION
				"Description."
			::= { tpu1cNotificationAuxData 10 }

		
--       1.3.6.1.4.1.6346.1.8.12.2.11
-- 1.3.6.1.4.1.6346.1.8.12.2.11
-- 1.3.6.1.4.1.6346.1.8.12.2.11
-- 1.3.6.1.4.1.6346.1.8.12.2.11
-- 1.3.6.1.4.1.6346.1.8.12.2.11
-- 1.3.6.1.4.1.6346.1.8.12.2.11
		-- 1.3.6.1.4.1.6346.1.8.12.2.11
		tpu1cNotifyOutputCurrentState OBJECT-TYPE
			SYNTAX BITS
				{
				out1(0),
				out2(1),
				out3(2),
				out4(3),
				out5(4),
				out6(5),
				out7(6),
				out8(7),
				out9(8),
				out10(9),
				out11(10),
				out12(11),
				out13(12),
				out14(13),
				out15(14),
				out16(15),
				out17(16),
				out18(17),
				out19(18),
				out20(19),
				out21(20),
				out22(21),
				out23(22),
				out24(23),
				out25(24),
				out26(25),
				out27(26),
				out28(27),
				out29(28),
				out30(29),
				out31(30),
				out32(31)
				}
			MAX-ACCESS read-only
			STATUS current
			DESCRIPTION
				"Description."
			::= { tpu1cNotificationAuxData 11 }

		
--       1.3.6.1.4.1.6346.1.8.12.2.12
-- 1.3.6.1.4.1.6346.1.8.12.2.12
-- 1.3.6.1.4.1.6346.1.8.12.2.12
-- 1.3.6.1.4.1.6346.1.8.12.2.12
-- 1.3.6.1.4.1.6346.1.8.12.2.12
-- 1.3.6.1.4.1.6346.1.8.12.2.12
		-- 1.3.6.1.4.1.6346.1.8.12.2.12
		tpu1cNotifyCounterValue OBJECT-TYPE
			SYNTAX Counter32
			MAX-ACCESS read-only
			STATUS current
			DESCRIPTION
				"Description."
			::= { tpu1cNotificationAuxData 12 }

		
--      1.3.6.1.4.1.6346.1.8.12.2.13
-- 1.3.6.1.4.1.6346.1.8.12.2.13
-- 1.3.6.1.4.1.6346.1.8.12.2.13
-- 1.3.6.1.4.1.6346.1.8.12.2.13
-- 1.3.6.1.4.1.6346.1.8.12.2.13
		-- 1.3.6.1.4.1.6346.1.8.12.2.13
		tpu1cNotifyChannelAlarmStatusHigh OBJECT-TYPE
			SYNTAX BITS { sfp1NotDetected(0) }
			MAX-ACCESS read-write
			STATUS current
			DESCRIPTION
				"Description."
			::= { tpu1cNotificationAuxData 13 }

		
--     1.3.6.1.4.1.6346.1.8.12.2.14
-- 1.3.6.1.4.1.6346.1.8.12.2.14
-- 1.3.6.1.4.1.6346.1.8.12.2.14
-- 1.3.6.1.4.1.6346.1.8.12.2.14
		-- 1.3.6.1.4.1.6346.1.8.12.2.14
		tpu1cNotifyLoopType OBJECT-TYPE
			SYNTAX BITS
				{
				loopNone(0),
				loopInternal(1),
				loopLine(2)
				}
			MAX-ACCESS read-write
			STATUS current
			DESCRIPTION
				"Description."
			::= { tpu1cNotificationAuxData 14 }

		
--   1.3.6.1.4.1.6346.1.8.12.2.15
-- 1.3.6.1.4.1.6346.1.8.12.2.15
		-- 1.3.6.1.4.1.6346.1.8.12.2.15
		tpu1cNotifyAlias OBJECT-TYPE
			SYNTAX OCTET STRING
			MAX-ACCESS read-only
			STATUS current
			DESCRIPTION
				"Description."
			::= { tpu1cNotificationAuxData 15 }

		
--       1.3.6.1.4.1.6346.1.8.12.3
-- 1.3.6.1.4.1.6346.1.8.12.3
-- 1.3.6.1.4.1.6346.1.8.12.3
-- 1.3.6.1.4.1.6346.1.8.12.3
-- 1.3.6.1.4.1.6346.1.8.12.3
-- 1.3.6.1.4.1.6346.1.8.12.3
		-- 1.3.6.1.4.1.6346.1.8.12.3
		tpu1cNotificationSystemEvents OBJECT IDENTIFIER ::= { tpu1cNotifications 3 }

		
--       1.3.6.1.4.1.6346.1.8.12.3.1
-- 1.3.6.1.4.1.6346.1.8.12.3.1
-- 1.3.6.1.4.1.6346.1.8.12.3.1
-- 1.3.6.1.4.1.6346.1.8.12.3.1
-- 1.3.6.1.4.1.6346.1.8.12.3.1
-- 1.3.6.1.4.1.6346.1.8.12.3.1
		-- 1.3.6.1.4.1.6346.1.8.12.3.1
		tpu1cNotifySystemInit NOTIFICATION-TYPE
			OBJECTS { tpu1cNotifyTimeSecsUtc, tpu1cNotifyTimeMillisecs }
			STATUS current
			DESCRIPTION 
				"Description."
			::= { tpu1cNotificationSystemEvents 1 }

		
--       1.3.6.1.4.1.6346.1.8.12.3.2
-- 1.3.6.1.4.1.6346.1.8.12.3.2
-- 1.3.6.1.4.1.6346.1.8.12.3.2
-- 1.3.6.1.4.1.6346.1.8.12.3.2
-- 1.3.6.1.4.1.6346.1.8.12.3.2
-- 1.3.6.1.4.1.6346.1.8.12.3.2
		-- 1.3.6.1.4.1.6346.1.8.12.3.2
		tpu1cNotifyManualSignalingRelayRelease NOTIFICATION-TYPE
			OBJECTS { tpu1cNotifyTimeSecsUtc, tpu1cNotifyTimeMillisecs }
			STATUS current
			DESCRIPTION 
				"Description."
			::= { tpu1cNotificationSystemEvents 2 }

		
--     1.3.6.1.4.1.6346.1.8.12.3.3
-- 1.3.6.1.4.1.6346.1.8.12.3.3
-- 1.3.6.1.4.1.6346.1.8.12.3.3
-- 1.3.6.1.4.1.6346.1.8.12.3.3
		-- 1.3.6.1.4.1.6346.1.8.12.3.3
		tpu1cNotifyLoopChange NOTIFICATION-TYPE
			OBJECTS { tpu1cNotifyTimeSecsUtc, tpu1cNotifyTimeMillisecs, tpu1cNotifyLoopType }
			STATUS current
			DESCRIPTION 
				"Description."
			::= { tpu1cNotificationSystemEvents 3 }

		
--       1.3.6.1.4.1.6346.1.8.12.4
-- 1.3.6.1.4.1.6346.1.8.12.4
-- 1.3.6.1.4.1.6346.1.8.12.4
-- 1.3.6.1.4.1.6346.1.8.12.4
-- 1.3.6.1.4.1.6346.1.8.12.4
-- 1.3.6.1.4.1.6346.1.8.12.4
		-- 1.3.6.1.4.1.6346.1.8.12.4
		tpu1cNotificationSystemAlarms OBJECT IDENTIFIER ::= { tpu1cNotifications 4 }

		
--       1.3.6.1.4.1.6346.1.8.12.4.1
-- 1.3.6.1.4.1.6346.1.8.12.4.1
-- 1.3.6.1.4.1.6346.1.8.12.4.1
-- 1.3.6.1.4.1.6346.1.8.12.4.1
-- 1.3.6.1.4.1.6346.1.8.12.4.1
-- 1.3.6.1.4.1.6346.1.8.12.4.1
		-- 1.3.6.1.4.1.6346.1.8.12.4.1
		tpu1cNotifyRtcExternalSyncLost NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 1 }

		
--       1.3.6.1.4.1.6346.1.8.12.4.2
-- 1.3.6.1.4.1.6346.1.8.12.4.2
-- 1.3.6.1.4.1.6346.1.8.12.4.2
-- 1.3.6.1.4.1.6346.1.8.12.4.2
-- 1.3.6.1.4.1.6346.1.8.12.4.2
-- 1.3.6.1.4.1.6346.1.8.12.4.2
		-- 1.3.6.1.4.1.6346.1.8.12.4.2
		tpu1cNotifyEthLink61850Error NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 2 }

		
--       1.3.6.1.4.1.6346.1.8.12.4.3
-- 1.3.6.1.4.1.6346.1.8.12.4.3
-- 1.3.6.1.4.1.6346.1.8.12.4.3
-- 1.3.6.1.4.1.6346.1.8.12.4.3
-- 1.3.6.1.4.1.6346.1.8.12.4.3
-- 1.3.6.1.4.1.6346.1.8.12.4.3
		-- 1.3.6.1.4.1.6346.1.8.12.4.3
		tpu1cNotifyPowerSupplyFail NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 3 }

		
--       1.3.6.1.4.1.6346.1.8.12.4.4
-- 1.3.6.1.4.1.6346.1.8.12.4.4
-- 1.3.6.1.4.1.6346.1.8.12.4.4
-- 1.3.6.1.4.1.6346.1.8.12.4.4
-- 1.3.6.1.4.1.6346.1.8.12.4.4
-- 1.3.6.1.4.1.6346.1.8.12.4.4
		-- 1.3.6.1.4.1.6346.1.8.12.4.4
		tpu1cNotifyTeleMetryLinkError NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 4 }

		
--       1.3.6.1.4.1.6346.1.8.12.4.5
-- 1.3.6.1.4.1.6346.1.8.12.4.5
-- 1.3.6.1.4.1.6346.1.8.12.4.5
-- 1.3.6.1.4.1.6346.1.8.12.4.5
-- 1.3.6.1.4.1.6346.1.8.12.4.5
-- 1.3.6.1.4.1.6346.1.8.12.4.5
		-- 1.3.6.1.4.1.6346.1.8.12.4.5
		tpu1cNotifyModuleError NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 5 }

		
--       1.3.6.1.4.1.6346.1.8.12.4.6
-- 1.3.6.1.4.1.6346.1.8.12.4.6
-- 1.3.6.1.4.1.6346.1.8.12.4.6
-- 1.3.6.1.4.1.6346.1.8.12.4.6
-- 1.3.6.1.4.1.6346.1.8.12.4.6
-- 1.3.6.1.4.1.6346.1.8.12.4.6
		-- 1.3.6.1.4.1.6346.1.8.12.4.6
		tpu1cNotifyGenRemAlarm NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 6 }

		
--   1.3.6.1.4.1.6346.1.8.12.4.7
-- 1.3.6.1.4.1.6346.1.8.12.4.7
		-- 1.3.6.1.4.1.6346.1.8.12.4.7
		tpu1cNotifyEth2Link61850Error NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 7 }

		
--   1.3.6.1.4.1.6346.1.8.12.4.8
-- 1.3.6.1.4.1.6346.1.8.12.4.8
		-- 1.3.6.1.4.1.6346.1.8.12.4.8
		tpu1NotifyEnedisMhS NOTIFICATION-TYPE
			OBJECTS { tpu1cNotifyTimeSecsUtc, tpu1cNotifyTimeMillisecs, tpu1cNotifySystemAlarmStatus, tpu1cNotifyState }
			STATUS current
			DESCRIPTION 
				"Description."
			::= { tpu1cNotificationSystemAlarms 8 }

		
--       1.3.6.1.4.1.6346.1.8.12.5
-- 1.3.6.1.4.1.6346.1.8.12.5
-- 1.3.6.1.4.1.6346.1.8.12.5
-- 1.3.6.1.4.1.6346.1.8.12.5
-- 1.3.6.1.4.1.6346.1.8.12.5
-- 1.3.6.1.4.1.6346.1.8.12.5
		-- 1.3.6.1.4.1.6346.1.8.12.5
		tpu1cNotificationChannelAlarms OBJECT IDENTIFIER ::= { tpu1cNotifications 5 }

		
--       1.3.6.1.4.1.6346.1.8.12.5.1
-- 1.3.6.1.4.1.6346.1.8.12.5.1
-- 1.3.6.1.4.1.6346.1.8.12.5.1
-- 1.3.6.1.4.1.6346.1.8.12.5.1
-- 1.3.6.1.4.1.6346.1.8.12.5.1
-- 1.3.6.1.4.1.6346.1.8.12.5.1
		-- 1.3.6.1.4.1.6346.1.8.12.5.1
		tpu1cNotifyManualBlocking NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 1 }

		
--       1.3.6.1.4.1.6346.1.8.12.5.2
-- 1.3.6.1.4.1.6346.1.8.12.5.2
-- 1.3.6.1.4.1.6346.1.8.12.5.2
-- 1.3.6.1.4.1.6346.1.8.12.5.2
-- 1.3.6.1.4.1.6346.1.8.12.5.2
-- 1.3.6.1.4.1.6346.1.8.12.5.2
		-- 1.3.6.1.4.1.6346.1.8.12.5.2
		tpu1cNotifyLineTestError NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 2 }

		
--       1.3.6.1.4.1.6346.1.8.12.5.3
-- 1.3.6.1.4.1.6346.1.8.12.5.3
-- 1.3.6.1.4.1.6346.1.8.12.5.3
-- 1.3.6.1.4.1.6346.1.8.12.5.3
-- 1.3.6.1.4.1.6346.1.8.12.5.3
-- 1.3.6.1.4.1.6346.1.8.12.5.3
		-- 1.3.6.1.4.1.6346.1.8.12.5.3
		tpu1cNotifyIdentifyCodeError NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 3 }

		
--       1.3.6.1.4.1.6346.1.8.12.5.4
-- 1.3.6.1.4.1.6346.1.8.12.5.4
-- 1.3.6.1.4.1.6346.1.8.12.5.4
-- 1.3.6.1.4.1.6346.1.8.12.5.4
-- 1.3.6.1.4.1.6346.1.8.12.5.4
-- 1.3.6.1.4.1.6346.1.8.12.5.4
		-- 1.3.6.1.4.1.6346.1.8.12.5.4
		tpu1cNotifySecurityCodeError NOTIFICATION-TYPE
			OBJECTS { tpu1cNotifyChannel, tpu1cNotifyTimeSecsUtc, tpu1cNotifyTimeMillisecs, tpu1cNotifyChannelAlarmStatus, tpu1cNotifyChannelAlarmStatusHigh, 
				tpu1cNotifyState, tpu1cChannelAlarmStatus }
			STATUS current
			DESCRIPTION 
				"Description."
			::= { tpu1cNotificationChannelAlarms 4 }

		
--       1.3.6.1.4.1.6346.1.8.12.5.5
-- 1.3.6.1.4.1.6346.1.8.12.5.5
-- 1.3.6.1.4.1.6346.1.8.12.5.5
-- 1.3.6.1.4.1.6346.1.8.12.5.5
-- 1.3.6.1.4.1.6346.1.8.12.5.5
-- 1.3.6.1.4.1.6346.1.8.12.5.5
		-- 1.3.6.1.4.1.6346.1.8.12.5.5
		tpu1cNotifySyncLoss NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 5 }

		
--       1.3.6.1.4.1.6346.1.8.12.5.6
-- 1.3.6.1.4.1.6346.1.8.12.5.6
-- 1.3.6.1.4.1.6346.1.8.12.5.6
-- 1.3.6.1.4.1.6346.1.8.12.5.6
-- 1.3.6.1.4.1.6346.1.8.12.5.6
-- 1.3.6.1.4.1.6346.1.8.12.5.6
		-- 1.3.6.1.4.1.6346.1.8.12.5.6
		tpu1cNotifyBitErrorRateHigh NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 6 }

		
--       1.3.6.1.4.1.6346.1.8.12.5.7
-- 1.3.6.1.4.1.6346.1.8.12.5.7
-- 1.3.6.1.4.1.6346.1.8.12.5.7
-- 1.3.6.1.4.1.6346.1.8.12.5.7
-- 1.3.6.1.4.1.6346.1.8.12.5.7
-- 1.3.6.1.4.1.6346.1.8.12.5.7
		-- 1.3.6.1.4.1.6346.1.8.12.5.7
		tpu1cNotifyReceiverBlocked NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 7 }

		
--       1.3.6.1.4.1.6346.1.8.12.5.8
-- 1.3.6.1.4.1.6346.1.8.12.5.8
-- 1.3.6.1.4.1.6346.1.8.12.5.8
-- 1.3.6.1.4.1.6346.1.8.12.5.8
-- 1.3.6.1.4.1.6346.1.8.12.5.8
-- 1.3.6.1.4.1.6346.1.8.12.5.8
		-- 1.3.6.1.4.1.6346.1.8.12.5.8
		tpu1cNotifySignalLoss NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 8 }

		
--       1.3.6.1.4.1.6346.1.8.12.5.9
-- 1.3.6.1.4.1.6346.1.8.12.5.9
-- 1.3.6.1.4.1.6346.1.8.12.5.9
-- 1.3.6.1.4.1.6346.1.8.12.5.9
-- 1.3.6.1.4.1.6346.1.8.12.5.9
-- 1.3.6.1.4.1.6346.1.8.12.5.9
		-- 1.3.6.1.4.1.6346.1.8.12.5.9
		tpu1cNotifyGuardLevelLow NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 9 }

		
--       1.3.6.1.4.1.6346.1.8.12.5.10
-- 1.3.6.1.4.1.6346.1.8.12.5.10
-- 1.3.6.1.4.1.6346.1.8.12.5.10
-- 1.3.6.1.4.1.6346.1.8.12.5.10
-- 1.3.6.1.4.1.6346.1.8.12.5.10
-- 1.3.6.1.4.1.6346.1.8.12.5.10
		-- 1.3.6.1.4.1.6346.1.8.12.5.10
		tpu1cNotifyGuardLevelExcess NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 10 }

		
--       1.3.6.1.4.1.6346.1.8.12.5.11
-- 1.3.6.1.4.1.6346.1.8.12.5.11
-- 1.3.6.1.4.1.6346.1.8.12.5.11
-- 1.3.6.1.4.1.6346.1.8.12.5.11
-- 1.3.6.1.4.1.6346.1.8.12.5.11
-- 1.3.6.1.4.1.6346.1.8.12.5.11
		-- 1.3.6.1.4.1.6346.1.8.12.5.11
		tpu1cNotifySignalNoiseRatioLow NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 11 }

		
--       1.3.6.1.4.1.6346.1.8.12.5.12
-- 1.3.6.1.4.1.6346.1.8.12.5.12
-- 1.3.6.1.4.1.6346.1.8.12.5.12
-- 1.3.6.1.4.1.6346.1.8.12.5.12
-- 1.3.6.1.4.1.6346.1.8.12.5.12
-- 1.3.6.1.4.1.6346.1.8.12.5.12
		-- 1.3.6.1.4.1.6346.1.8.12.5.12
		tpu1cNotifyReceiverError NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 12 }

		
--       1.3.6.1.4.1.6346.1.8.12.5.13
-- 1.3.6.1.4.1.6346.1.8.12.5.13
-- 1.3.6.1.4.1.6346.1.8.12.5.13
-- 1.3.6.1.4.1.6346.1.8.12.5.13
-- 1.3.6.1.4.1.6346.1.8.12.5.13
-- 1.3.6.1.4.1.6346.1.8.12.5.13
		-- 1.3.6.1.4.1.6346.1.8.12.5.13
		tpu1cNotifyMeanTransferDelay NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 13 }

		
--       1.3.6.1.4.1.6346.1.8.12.5.14
-- 1.3.6.1.4.1.6346.1.8.12.5.14
-- 1.3.6.1.4.1.6346.1.8.12.5.14
-- 1.3.6.1.4.1.6346.1.8.12.5.14
-- 1.3.6.1.4.1.6346.1.8.12.5.14
-- 1.3.6.1.4.1.6346.1.8.12.5.14
		-- 1.3.6.1.4.1.6346.1.8.12.5.14
		tpu1cNotifyFrameDelayVariation NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 14 }

		
--       1.3.6.1.4.1.6346.1.8.12.5.15
-- 1.3.6.1.4.1.6346.1.8.12.5.15
-- 1.3.6.1.4.1.6346.1.8.12.5.15
-- 1.3.6.1.4.1.6346.1.8.12.5.15
-- 1.3.6.1.4.1.6346.1.8.12.5.15
-- 1.3.6.1.4.1.6346.1.8.12.5.15
		-- 1.3.6.1.4.1.6346.1.8.12.5.15
		tpu1cNotifyFrameLossRatio NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 15 }

		
--       1.3.6.1.4.1.6346.1.8.12.5.16
-- 1.3.6.1.4.1.6346.1.8.12.5.16
-- 1.3.6.1.4.1.6346.1.8.12.5.16
-- 1.3.6.1.4.1.6346.1.8.12.5.16
-- 1.3.6.1.4.1.6346.1.8.12.5.16
-- 1.3.6.1.4.1.6346.1.8.12.5.16
		-- 1.3.6.1.4.1.6346.1.8.12.5.16
		tpu1cNotifyIPLinkFault NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 16 }

		
--       1.3.6.1.4.1.6346.1.8.12.5.17
-- 1.3.6.1.4.1.6346.1.8.12.5.17
-- 1.3.6.1.4.1.6346.1.8.12.5.17
-- 1.3.6.1.4.1.6346.1.8.12.5.17
-- 1.3.6.1.4.1.6346.1.8.12.5.17
-- 1.3.6.1.4.1.6346.1.8.12.5.17
		-- 1.3.6.1.4.1.6346.1.8.12.5.17
		tpu1cNotifyIpSyncLoss NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 17 }

		
--       1.3.6.1.4.1.6346.1.8.12.5.18
-- 1.3.6.1.4.1.6346.1.8.12.5.18
-- 1.3.6.1.4.1.6346.1.8.12.5.18
-- 1.3.6.1.4.1.6346.1.8.12.5.18
-- 1.3.6.1.4.1.6346.1.8.12.5.18
-- 1.3.6.1.4.1.6346.1.8.12.5.18
		-- 1.3.6.1.4.1.6346.1.8.12.5.18
		tpu1cNotifyToutInputIEC61850Cmd1 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 18 }

		
--       1.3.6.1.4.1.6346.1.8.12.5.19
-- 1.3.6.1.4.1.6346.1.8.12.5.19
-- 1.3.6.1.4.1.6346.1.8.12.5.19
-- 1.3.6.1.4.1.6346.1.8.12.5.19
-- 1.3.6.1.4.1.6346.1.8.12.5.19
-- 1.3.6.1.4.1.6346.1.8.12.5.19
		-- 1.3.6.1.4.1.6346.1.8.12.5.19
		tpu1cNotifyToutInputIEC61850Cmd2 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 19 }

		
--       1.3.6.1.4.1.6346.1.8.12.5.20
-- 1.3.6.1.4.1.6346.1.8.12.5.20
-- 1.3.6.1.4.1.6346.1.8.12.5.20
-- 1.3.6.1.4.1.6346.1.8.12.5.20
-- 1.3.6.1.4.1.6346.1.8.12.5.20
-- 1.3.6.1.4.1.6346.1.8.12.5.20
		-- 1.3.6.1.4.1.6346.1.8.12.5.20
		tpu1cNotifyToutInputIEC61850Cmd3 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 20 }

		
--       1.3.6.1.4.1.6346.1.8.12.5.21
-- 1.3.6.1.4.1.6346.1.8.12.5.21
-- 1.3.6.1.4.1.6346.1.8.12.5.21
-- 1.3.6.1.4.1.6346.1.8.12.5.21
-- 1.3.6.1.4.1.6346.1.8.12.5.21
-- 1.3.6.1.4.1.6346.1.8.12.5.21
		-- 1.3.6.1.4.1.6346.1.8.12.5.21
		tpu1cNotifyToutInputIEC61850Cmd4 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 21 }

		
--       1.3.6.1.4.1.6346.1.8.12.5.22
-- 1.3.6.1.4.1.6346.1.8.12.5.22
-- 1.3.6.1.4.1.6346.1.8.12.5.22
-- 1.3.6.1.4.1.6346.1.8.12.5.22
-- 1.3.6.1.4.1.6346.1.8.12.5.22
-- 1.3.6.1.4.1.6346.1.8.12.5.22
		-- 1.3.6.1.4.1.6346.1.8.12.5.22
		tpu1cNotifyToutInputIEC61850Cmd5 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 22 }

		
--       1.3.6.1.4.1.6346.1.8.12.5.23
-- 1.3.6.1.4.1.6346.1.8.12.5.23
-- 1.3.6.1.4.1.6346.1.8.12.5.23
-- 1.3.6.1.4.1.6346.1.8.12.5.23
-- 1.3.6.1.4.1.6346.1.8.12.5.23
-- 1.3.6.1.4.1.6346.1.8.12.5.23
		-- 1.3.6.1.4.1.6346.1.8.12.5.23
		tpu1cNotifyToutInputIEC61850Cmd6 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 23 }

		
--       1.3.6.1.4.1.6346.1.8.12.5.24
-- 1.3.6.1.4.1.6346.1.8.12.5.24
-- 1.3.6.1.4.1.6346.1.8.12.5.24
-- 1.3.6.1.4.1.6346.1.8.12.5.24
-- 1.3.6.1.4.1.6346.1.8.12.5.24
-- 1.3.6.1.4.1.6346.1.8.12.5.24
		-- 1.3.6.1.4.1.6346.1.8.12.5.24
		tpu1cNotifyToutInputIEC61850Cmd7 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 24 }

		
--       1.3.6.1.4.1.6346.1.8.12.5.25
-- 1.3.6.1.4.1.6346.1.8.12.5.25
-- 1.3.6.1.4.1.6346.1.8.12.5.25
-- 1.3.6.1.4.1.6346.1.8.12.5.25
-- 1.3.6.1.4.1.6346.1.8.12.5.25
-- 1.3.6.1.4.1.6346.1.8.12.5.25
		-- 1.3.6.1.4.1.6346.1.8.12.5.25
		tpu1cNotifyToutInputIEC61850Cmd8 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 25 }

		
--       1.3.6.1.4.1.6346.1.8.12.5.26
-- 1.3.6.1.4.1.6346.1.8.12.5.26
-- 1.3.6.1.4.1.6346.1.8.12.5.26
-- 1.3.6.1.4.1.6346.1.8.12.5.26
-- 1.3.6.1.4.1.6346.1.8.12.5.26
-- 1.3.6.1.4.1.6346.1.8.12.5.26
		-- 1.3.6.1.4.1.6346.1.8.12.5.26
		tpu1cNotifyToutInputIEC61850Cmd9 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 26 }

		
--       1.3.6.1.4.1.6346.1.8.12.5.27
-- 1.3.6.1.4.1.6346.1.8.12.5.27
-- 1.3.6.1.4.1.6346.1.8.12.5.27
-- 1.3.6.1.4.1.6346.1.8.12.5.27
-- 1.3.6.1.4.1.6346.1.8.12.5.27
-- 1.3.6.1.4.1.6346.1.8.12.5.27
		-- 1.3.6.1.4.1.6346.1.8.12.5.27
		tpu1cNotifyToutInputIEC61850Cmd10 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 27 }

		
--       1.3.6.1.4.1.6346.1.8.12.5.28
-- 1.3.6.1.4.1.6346.1.8.12.5.28
-- 1.3.6.1.4.1.6346.1.8.12.5.28
-- 1.3.6.1.4.1.6346.1.8.12.5.28
-- 1.3.6.1.4.1.6346.1.8.12.5.28
-- 1.3.6.1.4.1.6346.1.8.12.5.28
		-- 1.3.6.1.4.1.6346.1.8.12.5.28
		tpu1cNotifyToutInputIEC61850Cmd11 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 28 }

		
--       1.3.6.1.4.1.6346.1.8.12.5.29
-- 1.3.6.1.4.1.6346.1.8.12.5.29
-- 1.3.6.1.4.1.6346.1.8.12.5.29
-- 1.3.6.1.4.1.6346.1.8.12.5.29
-- 1.3.6.1.4.1.6346.1.8.12.5.29
-- 1.3.6.1.4.1.6346.1.8.12.5.29
		-- 1.3.6.1.4.1.6346.1.8.12.5.29
		tpu1cNotifyToutInputIEC61850Cmd12 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 29 }

		
--       1.3.6.1.4.1.6346.1.8.12.5.30
-- 1.3.6.1.4.1.6346.1.8.12.5.30
-- 1.3.6.1.4.1.6346.1.8.12.5.30
-- 1.3.6.1.4.1.6346.1.8.12.5.30
-- 1.3.6.1.4.1.6346.1.8.12.5.30
-- 1.3.6.1.4.1.6346.1.8.12.5.30
		-- 1.3.6.1.4.1.6346.1.8.12.5.30
		tpu1cNotifyToutInputIEC61850Cmd13 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 30 }

		
--       1.3.6.1.4.1.6346.1.8.12.5.31
-- 1.3.6.1.4.1.6346.1.8.12.5.31
-- 1.3.6.1.4.1.6346.1.8.12.5.31
-- 1.3.6.1.4.1.6346.1.8.12.5.31
-- 1.3.6.1.4.1.6346.1.8.12.5.31
-- 1.3.6.1.4.1.6346.1.8.12.5.31
		-- 1.3.6.1.4.1.6346.1.8.12.5.31
		tpu1cNotifyToutInputIEC61850Cmd14 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 31 }

		
--       1.3.6.1.4.1.6346.1.8.12.5.32
-- 1.3.6.1.4.1.6346.1.8.12.5.32
-- 1.3.6.1.4.1.6346.1.8.12.5.32
-- 1.3.6.1.4.1.6346.1.8.12.5.32
-- 1.3.6.1.4.1.6346.1.8.12.5.32
-- 1.3.6.1.4.1.6346.1.8.12.5.32
		-- 1.3.6.1.4.1.6346.1.8.12.5.32
		tpu1cNotifyToutInputIEC61850Cmd15 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 32 }

		
--       1.3.6.1.4.1.6346.1.8.12.5.33
-- 1.3.6.1.4.1.6346.1.8.12.5.33
-- 1.3.6.1.4.1.6346.1.8.12.5.33
-- 1.3.6.1.4.1.6346.1.8.12.5.33
-- 1.3.6.1.4.1.6346.1.8.12.5.33
-- 1.3.6.1.4.1.6346.1.8.12.5.33
		-- 1.3.6.1.4.1.6346.1.8.12.5.33
		tpu1cNotifyToutInputIEC61850Cmd16 NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 33 }

		
--       1.3.6.1.4.1.6346.1.8.12.5.34
-- 1.3.6.1.4.1.6346.1.8.12.5.34
-- 1.3.6.1.4.1.6346.1.8.12.5.34
-- 1.3.6.1.4.1.6346.1.8.12.5.34
-- 1.3.6.1.4.1.6346.1.8.12.5.34
-- 1.3.6.1.4.1.6346.1.8.12.5.34
		-- 1.3.6.1.4.1.6346.1.8.12.5.34
		tpu1cNotifyOutputIEC61850Command NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 34 }

		
--       1.3.6.1.4.1.6346.1.8.12.5.35
-- 1.3.6.1.4.1.6346.1.8.12.5.35
-- 1.3.6.1.4.1.6346.1.8.12.5.35
-- 1.3.6.1.4.1.6346.1.8.12.5.35
-- 1.3.6.1.4.1.6346.1.8.12.5.35
-- 1.3.6.1.4.1.6346.1.8.12.5.35
		-- 1.3.6.1.4.1.6346.1.8.12.5.35
		tpu1cNotifySystemIEC61850ClockFail NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 35 }

		
--       1.3.6.1.4.1.6346.1.8.12.5.36
-- 1.3.6.1.4.1.6346.1.8.12.5.36
-- 1.3.6.1.4.1.6346.1.8.12.5.36
-- 1.3.6.1.4.1.6346.1.8.12.5.36
-- 1.3.6.1.4.1.6346.1.8.12.5.36
-- 1.3.6.1.4.1.6346.1.8.12.5.36
		-- 1.3.6.1.4.1.6346.1.8.12.5.36
		tpu1NotifySignalLossDigitalIOCT NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 36 }

		
--       1.3.6.1.4.1.6346.1.8.12.5.37
-- 1.3.6.1.4.1.6346.1.8.12.5.37
-- 1.3.6.1.4.1.6346.1.8.12.5.37
-- 1.3.6.1.4.1.6346.1.8.12.5.37
-- 1.3.6.1.4.1.6346.1.8.12.5.37
-- 1.3.6.1.4.1.6346.1.8.12.5.37
		-- 1.3.6.1.4.1.6346.1.8.12.5.37
		tpu1NotifyRemoteAlarmIndicationIOCT NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 37 }

		
--       1.3.6.1.4.1.6346.1.8.12.5.38
-- 1.3.6.1.4.1.6346.1.8.12.5.38
-- 1.3.6.1.4.1.6346.1.8.12.5.38
-- 1.3.6.1.4.1.6346.1.8.12.5.38
-- 1.3.6.1.4.1.6346.1.8.12.5.38
-- 1.3.6.1.4.1.6346.1.8.12.5.38
		-- 1.3.6.1.4.1.6346.1.8.12.5.38
		tpu1NotifyC3794AIS NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 38 }

		
--       1.3.6.1.4.1.6346.1.8.12.5.39
-- 1.3.6.1.4.1.6346.1.8.12.5.39
-- 1.3.6.1.4.1.6346.1.8.12.5.39
-- 1.3.6.1.4.1.6346.1.8.12.5.39
-- 1.3.6.1.4.1.6346.1.8.12.5.39
-- 1.3.6.1.4.1.6346.1.8.12.5.39
		-- 1.3.6.1.4.1.6346.1.8.12.5.39
		tpu1NotifyC3794LOS NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 39 }

		
--       1.3.6.1.4.1.6346.1.8.12.5.40
-- 1.3.6.1.4.1.6346.1.8.12.5.40
-- 1.3.6.1.4.1.6346.1.8.12.5.40
-- 1.3.6.1.4.1.6346.1.8.12.5.40
-- 1.3.6.1.4.1.6346.1.8.12.5.40
-- 1.3.6.1.4.1.6346.1.8.12.5.40
		-- 1.3.6.1.4.1.6346.1.8.12.5.40
		tpu1NotifyC3794PathYellow NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 40 }

		
--       1.3.6.1.4.1.6346.1.8.12.5.41
-- 1.3.6.1.4.1.6346.1.8.12.5.41
-- 1.3.6.1.4.1.6346.1.8.12.5.41
-- 1.3.6.1.4.1.6346.1.8.12.5.41
-- 1.3.6.1.4.1.6346.1.8.12.5.41
-- 1.3.6.1.4.1.6346.1.8.12.5.41
		-- 1.3.6.1.4.1.6346.1.8.12.5.41
		tpu1NotifySfpTempAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 41 }

		
--       1.3.6.1.4.1.6346.1.8.12.5.42
-- 1.3.6.1.4.1.6346.1.8.12.5.42
-- 1.3.6.1.4.1.6346.1.8.12.5.42
-- 1.3.6.1.4.1.6346.1.8.12.5.42
-- 1.3.6.1.4.1.6346.1.8.12.5.42
-- 1.3.6.1.4.1.6346.1.8.12.5.42
		-- 1.3.6.1.4.1.6346.1.8.12.5.42
		tpu1NotifySfpVccAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 42 }

		
--       1.3.6.1.4.1.6346.1.8.12.5.43
-- 1.3.6.1.4.1.6346.1.8.12.5.43
-- 1.3.6.1.4.1.6346.1.8.12.5.43
-- 1.3.6.1.4.1.6346.1.8.12.5.43
-- 1.3.6.1.4.1.6346.1.8.12.5.43
-- 1.3.6.1.4.1.6346.1.8.12.5.43
		-- 1.3.6.1.4.1.6346.1.8.12.5.43
		tpu1NotifySfpBiasAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 43 }

		
--       1.3.6.1.4.1.6346.1.8.12.5.44
-- 1.3.6.1.4.1.6346.1.8.12.5.44
-- 1.3.6.1.4.1.6346.1.8.12.5.44
-- 1.3.6.1.4.1.6346.1.8.12.5.44
-- 1.3.6.1.4.1.6346.1.8.12.5.44
-- 1.3.6.1.4.1.6346.1.8.12.5.44
		-- 1.3.6.1.4.1.6346.1.8.12.5.44
		tpu1NotifySfpTxPowerAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 44 }

		
--       1.3.6.1.4.1.6346.1.8.12.5.45
-- 1.3.6.1.4.1.6346.1.8.12.5.45
-- 1.3.6.1.4.1.6346.1.8.12.5.45
-- 1.3.6.1.4.1.6346.1.8.12.5.45
-- 1.3.6.1.4.1.6346.1.8.12.5.45
-- 1.3.6.1.4.1.6346.1.8.12.5.45
		-- 1.3.6.1.4.1.6346.1.8.12.5.45
		tpu1NotifySfpRxPowerAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 45 }

		
--       1.3.6.1.4.1.6346.1.8.12.5.46
-- 1.3.6.1.4.1.6346.1.8.12.5.46
-- 1.3.6.1.4.1.6346.1.8.12.5.46
-- 1.3.6.1.4.1.6346.1.8.12.5.46
-- 1.3.6.1.4.1.6346.1.8.12.5.46
-- 1.3.6.1.4.1.6346.1.8.12.5.46
		-- 1.3.6.1.4.1.6346.1.8.12.5.46
		tpu1NotifySfpTempWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 46 }

		
--       1.3.6.1.4.1.6346.1.8.12.5.47
-- 1.3.6.1.4.1.6346.1.8.12.5.47
-- 1.3.6.1.4.1.6346.1.8.12.5.47
-- 1.3.6.1.4.1.6346.1.8.12.5.47
-- 1.3.6.1.4.1.6346.1.8.12.5.47
-- 1.3.6.1.4.1.6346.1.8.12.5.47
		-- 1.3.6.1.4.1.6346.1.8.12.5.47
		tpu1NotifySfpVccWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 47 }

		
--       1.3.6.1.4.1.6346.1.8.12.5.48
-- 1.3.6.1.4.1.6346.1.8.12.5.48
-- 1.3.6.1.4.1.6346.1.8.12.5.48
-- 1.3.6.1.4.1.6346.1.8.12.5.48
-- 1.3.6.1.4.1.6346.1.8.12.5.48
-- 1.3.6.1.4.1.6346.1.8.12.5.48
		-- 1.3.6.1.4.1.6346.1.8.12.5.48
		tpu1NotifySfpBiasWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 48 }

		
--       1.3.6.1.4.1.6346.1.8.12.5.49
-- 1.3.6.1.4.1.6346.1.8.12.5.49
-- 1.3.6.1.4.1.6346.1.8.12.5.49
-- 1.3.6.1.4.1.6346.1.8.12.5.49
-- 1.3.6.1.4.1.6346.1.8.12.5.49
-- 1.3.6.1.4.1.6346.1.8.12.5.49
		-- 1.3.6.1.4.1.6346.1.8.12.5.49
		tpu1NotifySfpTxPowerWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 49 }

		
--       1.3.6.1.4.1.6346.1.8.12.5.50
-- 1.3.6.1.4.1.6346.1.8.12.5.50
-- 1.3.6.1.4.1.6346.1.8.12.5.50
-- 1.3.6.1.4.1.6346.1.8.12.5.50
-- 1.3.6.1.4.1.6346.1.8.12.5.50
-- 1.3.6.1.4.1.6346.1.8.12.5.50
		-- 1.3.6.1.4.1.6346.1.8.12.5.50
		tpu1NotifySfpRxPowerWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 50 }

		
--       1.3.6.1.4.1.6346.1.8.12.5.51
-- 1.3.6.1.4.1.6346.1.8.12.5.51
-- 1.3.6.1.4.1.6346.1.8.12.5.51
-- 1.3.6.1.4.1.6346.1.8.12.5.51
-- 1.3.6.1.4.1.6346.1.8.12.5.51
-- 1.3.6.1.4.1.6346.1.8.12.5.51
		-- 1.3.6.1.4.1.6346.1.8.12.5.51
		tpu1NotifySfpNotDetected NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 51 }

		
--   1.3.6.1.4.1.6346.1.8.12.5.52
-- 1.3.6.1.4.1.6346.1.8.12.5.52
		-- 1.3.6.1.4.1.6346.1.8.12.5.52
		tpu1NotifyIpTxTrans NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 52 }

		
--   1.3.6.1.4.1.6346.1.8.12.5.53
-- 1.3.6.1.4.1.6346.1.8.12.5.53
		-- 1.3.6.1.4.1.6346.1.8.12.5.53
		tpu1NotifyInvCmdTx NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 53 }

		
--   1.3.6.1.4.1.6346.1.8.12.5.54
-- 1.3.6.1.4.1.6346.1.8.12.5.54
		-- 1.3.6.1.4.1.6346.1.8.12.5.54
		tpu1NotifyInvCmdRx NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 54 }

		
--   1.3.6.1.4.1.6346.1.8.12.5.55
-- 1.3.6.1.4.1.6346.1.8.12.5.55
		-- 1.3.6.1.4.1.6346.1.8.12.5.55
		tpu1NotifySfp2TempAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 55 }

		
--   1.3.6.1.4.1.6346.1.8.12.5.56
-- 1.3.6.1.4.1.6346.1.8.12.5.56
		-- 1.3.6.1.4.1.6346.1.8.12.5.56
		tpu1NotifySfp2VccAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 56 }

		
--   1.3.6.1.4.1.6346.1.8.12.5.57
-- 1.3.6.1.4.1.6346.1.8.12.5.57
		-- 1.3.6.1.4.1.6346.1.8.12.5.57
		tpu1NotifySfp2BiasAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 57 }

		
--   1.3.6.1.4.1.6346.1.8.12.5.58
-- 1.3.6.1.4.1.6346.1.8.12.5.58
		-- 1.3.6.1.4.1.6346.1.8.12.5.58
		tpu1NotifySfp2TxPowerAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 58 }

		
--   1.3.6.1.4.1.6346.1.8.12.5.59
-- 1.3.6.1.4.1.6346.1.8.12.5.59
		-- 1.3.6.1.4.1.6346.1.8.12.5.59
		tpu1NotifySfp2RxPowerAlarm NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 59 }

		
--   1.3.6.1.4.1.6346.1.8.12.5.60
-- 1.3.6.1.4.1.6346.1.8.12.5.60
		-- 1.3.6.1.4.1.6346.1.8.12.5.60
		tpu1NotifySfp2TempWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 60 }

		
--   1.3.6.1.4.1.6346.1.8.12.5.61
-- 1.3.6.1.4.1.6346.1.8.12.5.61
		-- 1.3.6.1.4.1.6346.1.8.12.5.61
		tpu1NotifySfp2VccWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 61 }

		
--   1.3.6.1.4.1.6346.1.8.12.5.62
-- 1.3.6.1.4.1.6346.1.8.12.5.62
		-- 1.3.6.1.4.1.6346.1.8.12.5.62
		tpu1NotifySfp2BiasWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 62 }

		
--   1.3.6.1.4.1.6346.1.8.12.5.63
-- 1.3.6.1.4.1.6346.1.8.12.5.63
		-- 1.3.6.1.4.1.6346.1.8.12.5.63
		tpu1NotifySfp2TxPowerWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 63 }

		
--   1.3.6.1.4.1.6346.1.8.12.5.64
-- 1.3.6.1.4.1.6346.1.8.12.5.64
		-- 1.3.6.1.4.1.6346.1.8.12.5.64
		tpu1NotifySfp2RxPowerWarn NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 64 }

		
--   1.3.6.1.4.1.6346.1.8.12.5.65
-- 1.3.6.1.4.1.6346.1.8.12.5.65
		-- 1.3.6.1.4.1.6346.1.8.12.5.65
		tpu1NotifySfp2NotDetected NOTIFICATION-TYPE
			OBJECTS { tpu1cNotifyChannel, tpu1cNotifyTimeSecsUtc, tpu1cNotifyTimeMillisecs, tpu1cNotifyChannelAlarmStatusHigh, tpu1cNotifyChannelAlarmStatus, 
				tpu1cNotifyState }
			STATUS current
			DESCRIPTION 
				"Description."
			::= { tpu1cNotificationChannelAlarms 65 }

		
--       1.3.6.1.4.1.6346.1.8.12.7
-- 1.3.6.1.4.1.6346.1.8.12.7
-- 1.3.6.1.4.1.6346.1.8.12.6
-- 1.3.6.1.4.1.6346.1.8.12.6
-- 1.3.6.1.4.1.6346.1.8.12.7
-- 1.3.6.1.4.1.6346.1.8.12.7
		-- 1.3.6.1.4.1.6346.1.8.12.6
		tpu1cNotificationCommands OBJECT IDENTIFIER ::= { tpu1cNotifications 6 }

		
--       1.3.6.1.4.1.6346.1.8.12.7.1
-- 1.3.6.1.4.1.6346.1.8.12.7.1
-- 1.3.6.1.4.1.6346.1.8.12.6.1
-- 1.3.6.1.4.1.6346.1.8.12.6.1
-- 1.3.6.1.4.1.6346.1.8.12.7.1
-- 1.3.6.1.4.1.6346.1.8.12.7.1
		-- 1.3.6.1.4.1.6346.1.8.12.6.1
		tpu1cNotifyCommandTx NOTIFICATION-TYPE
			OBJECTS { tpu1cNotifyState, tpu1cNotifyTimeSecsUtc, tpu1cNotifyTimeMillisecs, tpu1cNotifyCounterValue, tpu1cNotifyCmdCurrentState, 
				tpu1cNotifyCmdNum }
			STATUS current
			DESCRIPTION 
				"Description."
			::= { tpu1cNotificationCommands 1 }

		
--       1.3.6.1.4.1.6346.1.8.12.7.2
-- 1.3.6.1.4.1.6346.1.8.12.7.2
-- 1.3.6.1.4.1.6346.1.8.12.6.2
-- 1.3.6.1.4.1.6346.1.8.12.6.2
-- 1.3.6.1.4.1.6346.1.8.12.7.2
-- 1.3.6.1.4.1.6346.1.8.12.7.2
		-- 1.3.6.1.4.1.6346.1.8.12.6.2
		tpu1cNotifyCommandRx NOTIFICATION-TYPE
			OBJECTS { tpu1cNotifyState, tpu1cNotifyTimeSecsUtc, tpu1cNotifyTimeMillisecs, tpu1cNotifyCounterValue, tpu1cNotifyCmdCurrentState, 
				tpu1cNotifyCmdNum }
			STATUS current
			DESCRIPTION 
				"Description."
			::= { tpu1cNotificationCommands 2 }

		
--       1.3.6.1.4.1.6346.1.8.12.8
-- 1.3.6.1.4.1.6346.1.8.12.8
-- 1.3.6.1.4.1.6346.1.8.12.7
-- 1.3.6.1.4.1.6346.1.8.12.7
-- 1.3.6.1.4.1.6346.1.8.12.8
-- 1.3.6.1.4.1.6346.1.8.12.8
		-- 1.3.6.1.4.1.6346.1.8.12.7
		tpu1cNotificationIOCircuits OBJECT IDENTIFIER ::= { tpu1cNotifications 7 }

		
--       1.3.6.1.4.1.6346.1.8.12.8.1
-- 1.3.6.1.4.1.6346.1.8.12.8.1
-- 1.3.6.1.4.1.6346.1.8.12.7.1
-- 1.3.6.1.4.1.6346.1.8.12.7.1
-- 1.3.6.1.4.1.6346.1.8.12.8.1
-- 1.3.6.1.4.1.6346.1.8.12.8.1
		-- 1.3.6.1.4.1.6346.1.8.12.7.1
		tpu1cNotifyInputCircuits NOTIFICATION-TYPE
			OBJECTS { tpu1cNotifyState, tpu1cNotifyTimeSecsUtc, tpu1cNotifyTimeMillisecs, tpu1cNotifyCounterValue, tpu1cNotifyInputCurrentState, 
				tpu1cNotifyIONum }
			STATUS current
			DESCRIPTION 
				"Description."
			::= { tpu1cNotificationIOCircuits 1 }

		
--       1.3.6.1.4.1.6346.1.8.12.8.2
-- 1.3.6.1.4.1.6346.1.8.12.8.2
-- 1.3.6.1.4.1.6346.1.8.12.7.2
-- 1.3.6.1.4.1.6346.1.8.12.7.2
-- 1.3.6.1.4.1.6346.1.8.12.8.2
-- 1.3.6.1.4.1.6346.1.8.12.8.2
		-- 1.3.6.1.4.1.6346.1.8.12.7.2
		tpu1cNotifyOutputCircuits NOTIFICATION-TYPE
			OBJECTS { tpu1cNotifyState, tpu1cNotifyTimeSecsUtc, tpu1cNotifyTimeMillisecs, tpu1cNotifyCounterValue, tpu1cNotifyOutputCurrentState, 
				tpu1cNotifyIONum }
			STATUS current
			DESCRIPTION 
				"Description."
			::= { tpu1cNotificationIOCircuits 2 }

		
--       1.3.6.1.4.1.6346.1.8.12.9
-- 1.3.6.1.4.1.6346.1.8.12.9
-- 1.3.6.1.4.1.6346.1.8.12.8
-- 1.3.6.1.4.1.6346.1.8.12.8
-- 1.3.6.1.4.1.6346.1.8.12.9
-- 1.3.6.1.4.1.6346.1.8.12.9
		-- 1.3.6.1.4.1.6346.1.8.12.8
		tpu1cNotificationTelemetry OBJECT IDENTIFIER ::= { tpu1cNotifications 8 }

		
--       1.3.6.1.4.1.6346.1.8.12.9.1
-- 1.3.6.1.4.1.6346.1.8.12.9.1
-- 1.3.6.1.4.1.6346.1.8.12.8.1
-- 1.3.6.1.4.1.6346.1.8.12.8.1
-- 1.3.6.1.4.1.6346.1.8.12.9.1
-- 1.3.6.1.4.1.6346.1.8.12.9.1
		-- 1.3.6.1.4.1.6346.1.8.12.8.1
		tpu1cNotifyTelemetryDigitalInput NOTIFICATION-TYPE
			OBJECTS { tpu1cNotifyState, tpu1cNotifyTimeSecsUtc, tpu1cNotifyTimeMillisecs, tpu1cNotifyCounterValue, tpu1cNotifyInputCurrentState, 
				tpu1cNotifyIONum }
			STATUS current
			DESCRIPTION 
				"Description."
			::= { tpu1cNotificationTelemetry 1 }

		
--       1.3.6.1.4.1.6346.1.8.12.9.2
-- 1.3.6.1.4.1.6346.1.8.12.9.2
-- 1.3.6.1.4.1.6346.1.8.12.8.2
-- 1.3.6.1.4.1.6346.1.8.12.8.2
-- 1.3.6.1.4.1.6346.1.8.12.9.2
-- 1.3.6.1.4.1.6346.1.8.12.9.2
		-- 1.3.6.1.4.1.6346.1.8.12.8.2
		tpu1cNotifyTelemetryDigitalOutput NOTIFICATION-TYPE
			OBJECTS { tpu1cNotifyState, tpu1cNotifyTimeSecsUtc, tpu1cNotifyTimeMillisecs, tpu1cNotifyCounterValue, tpu1cNotifyOutputCurrentState, 
				tpu1cNotifyIONum }
			STATUS current
			DESCRIPTION 
				"Description."
			::= { tpu1cNotificationTelemetry 2 }

		
--   1.3.6.1.4.1.6346.1.8.12.10
-- 1.3.6.1.4.1.6346.1.8.12.10
		-- 1.3.6.1.4.1.6346.1.8.12.9
		tpuNotificationCybersecurity OBJECT IDENTIFIER ::= { tpu1cNotifications 9 }

		
--   1.3.6.1.4.1.6346.1.8.12.10.1
-- 1.3.6.1.4.1.6346.1.8.12.10.1
		-- 1.3.6.1.4.1.6346.1.8.12.9.1
		tpu1cNotifyConfigModification NOTIFICATION-TYPE
			OBJECTS { tpu1cNotifyTimeSecsUtc, tpu1cNotifyTimeMillisecs }
			STATUS current
			DESCRIPTION 
				"Description."
			::= { tpuNotificationCybersecurity 1 }

		
--   1.3.6.1.4.1.6346.1.8.12.10.2
-- 1.3.6.1.4.1.6346.1.8.12.10.2
		-- 1.3.6.1.4.1.6346.1.8.12.9.2
		tpu1cNotifyConfigModifLogin NOTIFICATION-TYPE
			OBJECTS { tpu1cNotifyTimeSecsUtc, tpu1cNotifyTimeMillisecs, tpu1cNotifyAlias }
			STATUS current
			DESCRIPTION 
				"Description."
			::= { tpuNotificationCybersecurity 2 }

		
--   1.3.6.1.4.1.6346.1.8.12.10.3
-- 1.3.6.1.4.1.6346.1.8.12.10.3
		-- 1.3.6.1.4.1.6346.1.8.12.9.3
		tpu1cNotifyConfigModifLoginBasic NOTIFICATION-TYPE
			OBJECTS { tpu1cNotifyTimeSecsUtc, tpu1cNotifyTimeMillisecs }
			STATUS current
			DESCRIPTION 
				"Description."
			::= { tpuNotificationCybersecurity 3 }

		
--   1.3.6.1.4.1.6346.1.8.12.10.4
-- 1.3.6.1.4.1.6346.1.8.12.10.4
		-- 1.3.6.1.4.1.6346.1.8.12.9.4
		tpu1cNotifyEnterLogin NOTIFICATION-TYPE
			OBJECTS { tpu1cNotifyTimeSecsUtc, tpu1cNotifyTimeMillisecs, tpu1cNotifyAlias }
			STATUS current
			DESCRIPTION 
				"Description."
			::= { tpuNotificationCybersecurity 4 }

		
--   1.3.6.1.4.1.6346.1.8.12.10.5
-- 1.3.6.1.4.1.6346.1.8.12.10.5
		-- 1.3.6.1.4.1.6346.1.8.12.9.5
		tpu1cNotifyEnterLoginBasic NOTIFICATION-TYPE
			OBJECTS { tpu1cNotifyTimeSecsUtc, tpu1cNotifyTimeMillisecs }
			STATUS current
			DESCRIPTION 
				"Description."
			::= { tpuNotificationCybersecurity 5 }

		
--   1.3.6.1.4.1.6346.1.8.12.10.6
-- 1.3.6.1.4.1.6346.1.8.12.10.6
		-- 1.3.6.1.4.1.6346.1.8.12.9.6
		tpu1cNotifyLogout NOTIFICATION-TYPE
			OBJECTS { tpu1cNotifyTimeSecsUtc, tpu1cNotifyTimeMillisecs, tpu1cNotifyAlias }
			STATUS current
			DESCRIPTION 
				"Description."
			::= { tpuNotificationCybersecurity 6 }

		
--   1.3.6.1.4.1.6346.1.8.12.10.7
-- 1.3.6.1.4.1.6346.1.8.12.10.7
		-- 1.3.6.1.4.1.6346.1.8.12.9.7
		tpu1cNotifyLogoutBasic NOTIFICATION-TYPE
			OBJECTS { tpu1cNotifyTimeSecsUtc, tpu1cNotifyTimeMillisecs }
			STATUS current
			DESCRIPTION 
				"Description."
			::= { tpuNotificationCybersecurity 7 }

		
--   1.3.6.1.4.1.6346.1.8.12.10.8
-- 1.3.6.1.4.1.6346.1.8.12.10.8
		-- 1.3.6.1.4.1.6346.1.8.12.9.8
		tpu1cNotifyEnterLoginFailed NOTIFICATION-TYPE
			OBJECTS { tpu1cNotifyTimeSecsUtc, tpu1cNotifyTimeMillisecs }
			STATUS current
			DESCRIPTION 
				"Description."
			::= { tpuNotificationCybersecurity 8 }

		
--   1.3.6.1.4.1.6346.1.8.12.10.9
-- 1.3.6.1.4.1.6346.1.8.12.10.9
		-- 1.3.6.1.4.1.6346.1.8.12.9.9
		tpu1cNotifyLoginBlocked NOTIFICATION-TYPE
			OBJECTS { tpu1cNotifyTimeSecsUtc, tpu1cNotifyTimeMillisecs }
			STATUS current
			DESCRIPTION 
				"Description."
			::= { tpuNotificationCybersecurity 9 }

		
--   1.3.6.1.4.1.6346.1.8.12.10.10
-- 1.3.6.1.4.1.6346.1.8.12.10.10
		-- 1.3.6.1.4.1.6346.1.8.12.9.10
		tpu1cNotifyChgVersionTpu1z01 NOTIFICATION-TYPE
			OBJECTS { tpu1cNotifyTimeSecsUtc, tpu1cNotifyTimeMillisecs }
			STATUS current
			DESCRIPTION 
				"Description."
			::= { tpuNotificationCybersecurity 10 }

		
--   1.3.6.1.4.1.6346.1.8.12.10.11
-- 1.3.6.1.4.1.6346.1.8.12.10.11
		-- 1.3.6.1.4.1.6346.1.8.12.9.11
		tpu1cNotifyChgVersionTpu1z02 NOTIFICATION-TYPE
			OBJECTS { tpu1cNotifyTimeSecsUtc, tpu1cNotifyTimeMillisecs }
			STATUS current
			DESCRIPTION 
				"Description."
			::= { tpuNotificationCybersecurity 11 }

		
--   1.3.6.1.4.1.6346.1.8.12.10.12
-- 1.3.6.1.4.1.6346.1.8.12.10.12
		-- 1.3.6.1.4.1.6346.1.8.12.9.12
		tpu1cNotifyChgVersionTpu1z03 NOTIFICATION-TYPE
			OBJECTS { tpu1cNotifyTimeSecsUtc, tpu1cNotifyTimeMillisecs }
			STATUS current
			DESCRIPTION 
				"Description."
			::= { tpuNotificationCybersecurity 12 }

		
--   1.3.6.1.4.1.6346.1.8.12.10.13
-- 1.3.6.1.4.1.6346.1.8.12.10.13
		-- 1.3.6.1.4.1.6346.1.8.12.9.13
		tpu1cNotifyChgVersionTpu1z04 NOTIFICATION-TYPE
			OBJECTS { tpu1cNotifyTimeSecsUtc, tpu1cNotifyTimeMillisecs }
			STATUS current
			DESCRIPTION 
				"Description."
			::= { tpuNotificationCybersecurity 13 }

		
--   1.3.6.1.4.1.6346.1.8.12.10.14
-- 1.3.6.1.4.1.6346.1.8.12.10.14
		-- 1.3.6.1.4.1.6346.1.8.12.9.14
		tpu1cNotifyChgVersionTpu1z05 NOTIFICATION-TYPE
			OBJECTS { tpu1cNotifyTimeSecsUtc, tpu1cNotifyTimeMillisecs }
			STATUS current
			DESCRIPTION 
				"Description."
			::= { tpuNotificationCybersecurity 14 }

		
--       1.3.6.1.4.1.6346.1.8.13
-- 1.3.6.1.4.1.6346.1.8.13
-- 1.3.6.1.4.1.6346.1.8.13
-- 1.3.6.1.4.1.6346.1.8.13
-- 1.3.6.1.4.1.6346.1.8.13
-- 1.3.6.1.4.1.6346.1.8.13
		-- 1.3.6.1.4.1.6346.1.8.13
		tpu1cMibConformance OBJECT IDENTIFIER ::= { tpu1c 13 }

		
--       1.3.6.1.4.1.6346.1.8.13.1
-- 1.3.6.1.4.1.6346.1.8.13.1
-- 1.3.6.1.4.1.6346.1.8.13.1
-- 1.3.6.1.4.1.6346.1.8.13.1
-- 1.3.6.1.4.1.6346.1.8.13.1
-- 1.3.6.1.4.1.6346.1.8.13.1
		-- 1.3.6.1.4.1.6346.1.8.13.1
		tpu1cMibGroups OBJECT IDENTIFIER ::= { tpu1cMibConformance 1 }

		
--       1.3.6.1.4.1.6346.1.8.13.1.1
-- 1.3.6.1.4.1.6346.1.8.13.1.1
-- 1.3.6.1.4.1.6346.1.8.13.1.1
-- 1.3.6.1.4.1.6346.1.8.13.1.1
-- 1.3.6.1.4.1.6346.1.8.13.1.1
-- 1.3.6.1.4.1.6346.1.8.13.1.1
		-- 1.3.6.1.4.1.6346.1.8.13.1.1
		tpu1cGroupIpNet OBJECT-GROUP
			OBJECTS { tpu1cIpNetAddrAddr, tpu1cIpNetMaskMask, tpu1cIpNetGateWay }
			STATUS current
			DESCRIPTION 
				"Description."
			::= { tpu1cMibGroups 1 }

		
--       1.3.6.1.4.1.6346.1.8.13.1.2
-- 1.3.6.1.4.1.6346.1.8.13.1.2
-- 1.3.6.1.4.1.6346.1.8.13.1.2
-- 1.3.6.1.4.1.6346.1.8.13.1.2
-- 1.3.6.1.4.1.6346.1.8.13.1.2
-- 1.3.6.1.4.1.6346.1.8.13.1.2
		-- 1.3.6.1.4.1.6346.1.8.13.1.2
		tpu1cGroupRealTimeClock OBJECT-GROUP
			OBJECTS { tpu1cRtcSynchro, tpu1cRtcSntpServer, tpu1cRtcValue }
			STATUS current
			DESCRIPTION 
				"Description."
			::= { tpu1cMibGroups 2 }

		
--       1.3.6.1.4.1.6346.1.8.13.1.3
-- 1.3.6.1.4.1.6346.1.8.13.1.3
-- 1.3.6.1.4.1.6346.1.8.13.1.3
-- 1.3.6.1.4.1.6346.1.8.13.1.3
-- 1.3.6.1.4.1.6346.1.8.13.1.3
-- 1.3.6.1.4.1.6346.1.8.13.1.3
		-- 1.3.6.1.4.1.6346.1.8.13.1.3
		tpu1cGroupCommands OBJECT-GROUP
			OBJECTS { tpu1cCmdTxCurrentState, tpu1cCmdTxCounterValue, tpu1cCmdRxCurrentState, tpu1cCmdRxCounterValue, tpu1cCmdRxCounterReset, 
				tpu1cCmdTxCounterReset }
			STATUS current
			DESCRIPTION 
				"Description."
			::= { tpu1cMibGroups 3 }

		
--       1.3.6.1.4.1.6346.1.8.13.1.4
-- 1.3.6.1.4.1.6346.1.8.13.1.4
-- 1.3.6.1.4.1.6346.1.8.13.1.4
-- 1.3.6.1.4.1.6346.1.8.13.1.4
-- 1.3.6.1.4.1.6346.1.8.13.1.4
-- 1.3.6.1.4.1.6346.1.8.13.1.4
		-- 1.3.6.1.4.1.6346.1.8.13.1.4
		tpu1cGroupIOCircuits OBJECT-GROUP
			OBJECTS { tpu1cCmdInputCircuitCurrentState, tpu1cCmdInputCircuitCounterReset, tpu1cCmdInputCircuitCounterValue, tpu1cCmdOutputCircuitCurrentState, tpu1cCmdOutputCircuitCounterReset, 
				tpu1cCmdOutputCircuitCounterValue }
			STATUS current
			DESCRIPTION 
				"Description."
			::= { tpu1cMibGroups 4 }

		
--       1.3.6.1.4.1.6346.1.8.13.1.5
-- 1.3.6.1.4.1.6346.1.8.13.1.5
-- 1.3.6.1.4.1.6346.1.8.13.1.5
-- 1.3.6.1.4.1.6346.1.8.13.1.5
-- 1.3.6.1.4.1.6346.1.8.13.1.5
-- 1.3.6.1.4.1.6346.1.8.13.1.5
		-- 1.3.6.1.4.1.6346.1.8.13.1.5
		tpu1cGroupTelemetry OBJECT-GROUP
			OBJECTS { tpu1cTelemetryDigitalInputCurrentState, tpu1cTelemetryDigitalInputCounterReset, tpu1cTelemetryDigitalInputCounterValue, tpu1cTelemetryDigitalOutputCurrentState, tpu1cTelemetryDigitalOutputCounterReset, 
				tpu1cTelemetryDigitalOutputCounterValue, tpu1cTelemetryAnalogInputCurValue, tpu1cTelemetryAnalogInputMaxValue, tpu1cTelemetryAnalogInputMinValue, tpu1cTelemetryAnalogInputMaxMinReset, 
				tpu1cTelemetryAnalogOutputCurValue, tpu1cTelemetryAnalogOutputMaxValue, tpu1cTelemetryAnalogOutputMinValue, tpu1cTelemetryAnalogOutputMaxMinReset }
			STATUS current
			DESCRIPTION 
				"Description."
			::= { tpu1cMibGroups 5 }

		
--       1.3.6.1.4.1.6346.1.8.13.1.6
-- 1.3.6.1.4.1.6346.1.8.13.1.6
-- 1.3.6.1.4.1.6346.1.8.13.1.6
-- 1.3.6.1.4.1.6346.1.8.13.1.6
-- 1.3.6.1.4.1.6346.1.8.13.1.6
-- 1.3.6.1.4.1.6346.1.8.13.1.6
		-- 1.3.6.1.4.1.6346.1.8.13.1.6
		tpu1cGroupChannelQuality OBJECT-GROUP
			OBJECTS { tpu1cSignalNoiseRatioValue, tpu1cBitErrorRateValue }
			STATUS current
			DESCRIPTION 
				"Description."
			::= { tpu1cMibGroups 6 }

		
--       1.3.6.1.4.1.6346.1.8.13.1.7
-- 1.3.6.1.4.1.6346.1.8.13.1.7
-- 1.3.6.1.4.1.6346.1.8.13.1.7
-- 1.3.6.1.4.1.6346.1.8.13.1.7
-- 1.3.6.1.4.1.6346.1.8.13.1.7
-- 1.3.6.1.4.1.6346.1.8.13.1.7
		-- 1.3.6.1.4.1.6346.1.8.13.1.7
		tpu1cGroupAlarmsStatus OBJECT-GROUP
			OBJECTS { tpu1cSystemAlarmStatus, tpu1cChannelAlarmStatus, tpu1cIeptAlarmStatus, tpu1cChannelAlarmStatusHigh }
			STATUS current
			DESCRIPTION 
				"Description."
			::= { tpu1cMibGroups 7 }

		
--       1.3.6.1.4.1.6346.1.8.13.1.8
-- 1.3.6.1.4.1.6346.1.8.13.1.8
-- 1.3.6.1.4.1.6346.1.8.13.1.8
-- 1.3.6.1.4.1.6346.1.8.13.1.8
-- 1.3.6.1.4.1.6346.1.8.13.1.8
-- 1.3.6.1.4.1.6346.1.8.13.1.8
		-- 1.3.6.1.4.1.6346.1.8.13.1.8
		tpu1cGroupEventsStatus OBJECT-GROUP
			OBJECTS { tpu1cSystemEventsStatus }
			STATUS current
			DESCRIPTION 
				"Description."
			::= { tpu1cMibGroups 8 }

		
--       1.3.6.1.4.1.6346.1.8.13.1.9
-- 1.3.6.1.4.1.6346.1.8.13.1.9
-- 1.3.6.1.4.1.6346.1.8.13.1.9
-- 1.3.6.1.4.1.6346.1.8.13.1.9
-- 1.3.6.1.4.1.6346.1.8.13.1.9
-- 1.3.6.1.4.1.6346.1.8.13.1.9
		-- 1.3.6.1.4.1.6346.1.8.13.1.9
		tpu1cGroupReset OBJECT-GROUP
			OBJECTS { tpu1cSystemResetAction }
			STATUS current
			DESCRIPTION 
				"Description."
			::= { tpu1cMibGroups 9 }

		
--       1.3.6.1.4.1.6346.1.8.13.1.10
-- 1.3.6.1.4.1.6346.1.8.13.1.10
-- 1.3.6.1.4.1.6346.1.8.13.1.10
-- 1.3.6.1.4.1.6346.1.8.13.1.10
-- 1.3.6.1.4.1.6346.1.8.13.1.10
-- 1.3.6.1.4.1.6346.1.8.13.1.10
		-- 1.3.6.1.4.1.6346.1.8.13.1.10
		tpu1cGroupNotificationsEnable OBJECT-GROUP
			OBJECTS { tpu1cNotificationEnableMask, tpu1cNotificationEnableMask2, tpu1cNotificationEnableMask3 }
			STATUS current
			DESCRIPTION 
				"Description."
			::= { tpu1cMibGroups 10 }

		
--       1.3.6.1.4.1.6346.1.8.13.1.11
-- 1.3.6.1.4.1.6346.1.8.13.1.11
-- 1.3.6.1.4.1.6346.1.8.13.1.11
-- 1.3.6.1.4.1.6346.1.8.13.1.11
-- 1.3.6.1.4.1.6346.1.8.13.1.11
-- 1.3.6.1.4.1.6346.1.8.13.1.11
		-- 1.3.6.1.4.1.6346.1.8.13.1.11
		tpu1cGroupNotificationsAuxData OBJECT-GROUP
			OBJECTS { tpu1cNotifyCmdNum, tpu1cNotifyIONum, tpu1cNotifyChannel, tpu1cNotifyState, tpu1cNotifyTimeSecsUtc, 
				tpu1cNotifyTimeMillisecs, tpu1cNotifySystemAlarmStatus, tpu1cNotifyChannelAlarmStatus, tpu1cNotifyCmdCurrentState, tpu1cNotifyInputCurrentState, 
				tpu1cNotifyOutputCurrentState, tpu1cNotifyCounterValue, tpu1cNotifyChannelAlarmStatusHigh, tpu1cNotifyLoopType, tpu1cNotifyAlias
				 }
			STATUS current
			DESCRIPTION 
				"Description."
			::= { tpu1cMibGroups 11 }

		
--       1.3.6.1.4.1.6346.1.8.13.1.12
-- 1.3.6.1.4.1.6346.1.8.13.1.12
-- 1.3.6.1.4.1.6346.1.8.13.1.12
-- 1.3.6.1.4.1.6346.1.8.13.1.12
-- 1.3.6.1.4.1.6346.1.8.13.1.12
-- 1.3.6.1.4.1.6346.1.8.13.1.12
		-- 1.3.6.1.4.1.6346.1.8.13.1.12
		tpu1cGroupNotificationsSystemEvents NOTIFICATION-GROUP
			NOTIFICATIONS { tpu1cNotifySystemInit, tpu1cNotifyManualSignalingRelayRelease, tpu1cNotifyLoopChange }
			STATUS current
			DESCRIPTION 
				"Description."
			::= { tpu1cMibGroups 12 }

		
--       1.3.6.1.4.1.6346.1.8.13.1.13
-- 1.3.6.1.4.1.6346.1.8.13.1.13
-- 1.3.6.1.4.1.6346.1.8.13.1.13
-- 1.3.6.1.4.1.6346.1.8.13.1.13
-- 1.3.6.1.4.1.6346.1.8.13.1.13
-- 1.3.6.1.4.1.6346.1.8.13.1.13
		-- 1.3.6.1.4.1.6346.1.8.13.1.13
		tpu1cGroupNotificationsSystemAlarms NOTIFICATION-GROUP
			NOTIFICATIONS { tpu1cNotifyRtcExternalSyncLost, tpu1cNotifyEthLink61850Error, tpu1cNotifyPowerSupplyFail, tpu1cNotifyGenRemAlarm, tpu1NotifyEnedisMhS, 
				tpu1cNotifyModuleError, tpu1cNotifyTeleMetryLinkError, tpu1cNotifyEth2Link61850Error }
			STATUS current
			DESCRIPTION 
				"Description."
			::= { tpu1cMibGroups 13 }

		
--       1.3.6.1.4.1.6346.1.8.13.1.14
-- 1.3.6.1.4.1.6346.1.8.13.1.14
-- 1.3.6.1.4.1.6346.1.8.13.1.14
-- 1.3.6.1.4.1.6346.1.8.13.1.14
-- 1.3.6.1.4.1.6346.1.8.13.1.14
-- 1.3.6.1.4.1.6346.1.8.13.1.14
		-- 1.3.6.1.4.1.6346.1.8.13.1.14
		tpu1cGroupNotificationsChannelAlarms NOTIFICATION-GROUP
			NOTIFICATIONS { tpu1cNotifyManualBlocking, tpu1cNotifyLineTestError, tpu1cNotifyIdentifyCodeError, tpu1cNotifySecurityCodeError, tpu1cNotifySyncLoss, 
				tpu1cNotifyBitErrorRateHigh, tpu1cNotifyReceiverBlocked, tpu1cNotifySignalLoss, tpu1cNotifyGuardLevelLow, tpu1cNotifyGuardLevelExcess, 
				tpu1cNotifySignalNoiseRatioLow, tpu1cNotifyReceiverError, tpu1NotifySignalLossDigitalIOCT, tpu1NotifyRemoteAlarmIndicationIOCT, tpu1NotifyC3794AIS, 
				tpu1NotifyC3794LOS, tpu1NotifyC3794PathYellow, tpu1NotifySfpTempAlarm, tpu1NotifySfpVccAlarm, tpu1NotifySfpBiasAlarm, 
				tpu1NotifySfpTxPowerAlarm, tpu1NotifySfpRxPowerAlarm, tpu1NotifySfpTempWarn, tpu1NotifySfpVccWarn, tpu1NotifySfpBiasWarn, 
				tpu1NotifySfpTxPowerWarn, tpu1NotifySfpRxPowerWarn }
			STATUS current
			DESCRIPTION 
				"Description."
			::= { tpu1cMibGroups 14 }

		
--       1.3.6.1.4.1.6346.1.8.13.1.15
-- 1.3.6.1.4.1.6346.1.8.13.1.15
-- 1.3.6.1.4.1.6346.1.8.13.1.15
-- 1.3.6.1.4.1.6346.1.8.13.1.15
-- 1.3.6.1.4.1.6346.1.8.13.1.15
-- 1.3.6.1.4.1.6346.1.8.13.1.15
		-- 1.3.6.1.4.1.6346.1.8.13.1.15
		tpu1cGroupNotificationsCommands NOTIFICATION-GROUP
			NOTIFICATIONS { tpu1cNotifyCommandTx, tpu1cNotifyCommandRx, tpu1cNotifyInputCircuits, tpu1cNotifyOutputCircuits }
			STATUS current
			DESCRIPTION 
				"Description."
			::= { tpu1cMibGroups 15 }

		
--       1.3.6.1.4.1.6346.1.8.13.1.16
-- 1.3.6.1.4.1.6346.1.8.13.1.16
-- 1.3.6.1.4.1.6346.1.8.13.1.16
-- 1.3.6.1.4.1.6346.1.8.13.1.16
-- 1.3.6.1.4.1.6346.1.8.13.1.16
-- 1.3.6.1.4.1.6346.1.8.13.1.16
		-- 1.3.6.1.4.1.6346.1.8.13.1.16
		tpu1cGroupNotificationsTelemetry NOTIFICATION-GROUP
			NOTIFICATIONS { tpu1cNotifyTelemetryDigitalInput, tpu1cNotifyTelemetryDigitalOutput }
			STATUS current
			DESCRIPTION 
				"Description."
			::= { tpu1cMibGroups 16 }

		
--   1.3.6.1.4.1.6346.1.8.13.1.17
-- 1.3.6.1.4.1.6346.1.8.13.1.17
		-- 1.3.6.1.4.1.6346.1.8.13.1.17
		tpu1cGroupNotificationsCybersec NOTIFICATION-GROUP
			NOTIFICATIONS { tpu1cNotifyConfigModification, tpu1cNotifyConfigModifLoginBasic, tpu1cNotifyEnterLoginBasic, tpu1cNotifyLogoutBasic, tpu1cNotifyEnterLoginFailed, 
				tpu1cNotifyLoginBlocked, tpu1cNotifyChgVersionTpu1z01, tpu1cNotifyChgVersionTpu1z02, tpu1cNotifyChgVersionTpu1z03, tpu1cNotifyChgVersionTpu1z04, 
				tpu1cNotifyChgVersionTpu1z05, tpu1cNotifyConfigModifLogin, tpu1cNotifyEnterLogin, tpu1cNotifyLogout }
			STATUS current
			DESCRIPTION 
				"Description."
			::= { tpu1cMibGroups 17 }

		
--       1.3.6.1.4.1.6346.1.8.13.1.17
-- 1.3.6.1.4.1.6346.1.8.13.1.17
-- 1.3.6.1.4.1.6346.1.8.13.1.17
-- 1.3.6.1.4.1.6346.1.8.13.1.17
-- 1.3.6.1.4.1.6346.1.8.13.1.18
-- 1.3.6.1.4.1.6346.1.8.13.1.18
		-- 1.3.6.1.4.1.6346.1.8.13.1.18
		tpu1cGroupNotificationsIpitAlarms NOTIFICATION-GROUP
			NOTIFICATIONS { tpu1cNotifyMeanTransferDelay, tpu1cNotifyIPLinkFault, tpu1cNotifyIpSyncLoss, tpu1cNotifyFrameDelayVariation, tpu1cNotifyFrameLossRatio
				 }
			STATUS current
			DESCRIPTION 
				"Description."
			::= { tpu1cMibGroups 18 }

		
--   1.3.6.1.4.1.6346.1.8.13.1.19
-- 1.3.6.1.4.1.6346.1.8.13.1.19
		-- 1.3.6.1.4.1.6346.1.8.13.1.19
		tpu1cGroupNotificationsIcptAlarms NOTIFICATION-GROUP
			NOTIFICATIONS { tpu1cNotifyMeanTransferDelay, tpu1cNotifyIPLinkFault, tpu1cNotifyFrameDelayVariation, tpu1cNotifyFrameLossRatio, tpu1cNotifyIpSyncLoss, 
				tpu1NotifyIpTxTrans, tpu1NotifySfp2TempAlarm, tpu1NotifySfp2VccAlarm, tpu1NotifySfp2BiasAlarm, tpu1NotifySfp2TxPowerAlarm, 
				tpu1NotifySfp2RxPowerAlarm, tpu1NotifySfp2TempWarn, tpu1NotifySfp2VccWarn, tpu1NotifySfp2BiasWarn, tpu1NotifySfp2TxPowerWarn, 
				tpu1NotifySfp2RxPowerWarn, tpu1NotifySfp2NotDetected }
			STATUS current
			DESCRIPTION 
				"Description."
			::= { tpu1cMibGroups 19 }

		
--       1.3.6.1.4.1.6346.1.8.13.1.18
-- 1.3.6.1.4.1.6346.1.8.13.1.18
-- 1.3.6.1.4.1.6346.1.8.13.1.18
-- 1.3.6.1.4.1.6346.1.8.13.1.18
-- 1.3.6.1.4.1.6346.1.8.13.1.20
-- 1.3.6.1.4.1.6346.1.8.13.1.20
		-- 1.3.6.1.4.1.6346.1.8.13.1.20
		tpu1cGroupNotificationsIeptAlarms NOTIFICATION-GROUP
			NOTIFICATIONS { tpu1cNotifyToutInputIEC61850Cmd1, tpu1cNotifyToutInputIEC61850Cmd2, tpu1cNotifyToutInputIEC61850Cmd3, tpu1cNotifyToutInputIEC61850Cmd4, tpu1cNotifyToutInputIEC61850Cmd5, 
				tpu1cNotifyToutInputIEC61850Cmd6, tpu1cNotifyToutInputIEC61850Cmd7, tpu1cNotifyToutInputIEC61850Cmd8, tpu1cNotifyToutInputIEC61850Cmd9, tpu1cNotifyToutInputIEC61850Cmd10, 
				tpu1cNotifyToutInputIEC61850Cmd11, tpu1cNotifyToutInputIEC61850Cmd12, tpu1cNotifyToutInputIEC61850Cmd13, tpu1cNotifyToutInputIEC61850Cmd14, tpu1cNotifyToutInputIEC61850Cmd15, 
				tpu1cNotifyToutInputIEC61850Cmd16, tpu1cNotifyOutputIEC61850Command, tpu1cNotifySystemIEC61850ClockFail }
			STATUS current
			DESCRIPTION 
				"Description."
			::= { tpu1cMibGroups 20 }

		
--       1.3.6.1.4.1.6346.1.8.13.1.19
-- 1.3.6.1.4.1.6346.1.8.13.1.19
-- 1.3.6.1.4.1.6346.1.8.13.1.19
-- 1.3.6.1.4.1.6346.1.8.13.1.19
-- 1.3.6.1.4.1.6346.1.8.13.1.21
-- 1.3.6.1.4.1.6346.1.8.13.1.21
		-- 1.3.6.1.4.1.6346.1.8.13.1.21
		tpu1cGroupNotificationsChannelHighAlarms NOTIFICATION-GROUP
			NOTIFICATIONS { tpu1NotifySfpNotDetected, tpu1NotifyIpTxTrans, tpu1NotifyInvCmdTx, tpu1NotifyInvCmdRx }
			STATUS current
			DESCRIPTION 
				"Description."
			::= { tpu1cMibGroups 21 }

		
--   1.3.6.1.4.1.6346.1.8.13.1.22
-- 1.3.6.1.4.1.6346.1.8.13.1.22
		-- 1.3.6.1.4.1.6346.1.8.13.1.22
		tpu1cGroupInfoSfp OBJECT-GROUP
			OBJECTS { tpu1cMeasIocsSfpTxBias, tpu1cMeasIocsSfpVcc, tpu1cMeasIocsSfpTemperature, tpu1cMeasIocsSfpRxPower, tpu1cInfoIocsSfpRange50mm, 
				tpu1cInfoIocsSfpRange9mm, tpu1cInfoIocsSfpRange62mm5, tpu1cInfoIocsSfpRangeCopper, tpu1cInfoIocsSfpWavelength, tpu1cInfoIocsSfpConnType, 
				tpu1cInfoIocsSfpModel, tpu1cInfoIocsSfpTxMedia, tpu1cInfoIocsSfpRevision, tpu1cInfoIocsSfpSerialNum, tpu1cMeasIocsSfpTxPower, 
				tpu1cInfoIocsSfpManufacturer }
			STATUS current
			DESCRIPTION 
				"Description."
			::= { tpu1cMibGroups 22 }

		
--   1.3.6.1.4.1.6346.1.8.13.1.23
-- 1.3.6.1.4.1.6346.1.8.13.1.23
		-- 1.3.6.1.4.1.6346.1.8.13.1.23
		tpu1cGroupCodeVersions OBJECT-GROUP
			OBJECTS { tpu1cTpu1z01Version, tpu1cTpu1z02Version, tpu1cTpu1z03Version, tpu1cTpu1z04Version, tpu1cTpu1z05Version
				 }
			STATUS current
			DESCRIPTION 
				"Description."
			::= { tpu1cMibGroups 23 }

		
--       1.3.6.1.4.1.6346.1.8.13.2
-- 1.3.6.1.4.1.6346.1.8.13.2
-- 1.3.6.1.4.1.6346.1.8.13.2
-- 1.3.6.1.4.1.6346.1.8.13.2
-- 1.3.6.1.4.1.6346.1.8.13.2
-- 1.3.6.1.4.1.6346.1.8.13.2
		-- 1.3.6.1.4.1.6346.1.8.13.2
		tpu1cMibCompliances OBJECT IDENTIFIER ::= { tpu1cMibConformance 2 }

		
--       1.3.6.1.4.1.6346.1.8.13.2.1
-- this module
-- 1.3.6.1.4.1.6346.1.8.13.2.1
-- this module
-- 1.3.6.1.4.1.6346.1.8.13.2.1
-- this module
-- 1.3.6.1.4.1.6346.1.8.13.2.1
-- this module
-- 1.3.6.1.4.1.6346.1.8.13.2.1
-- this module
-- 1.3.6.1.4.1.6346.1.8.13.2.1
-- this module
		-- 1.3.6.1.4.1.6346.1.8.13.2.1
		tpu1cBasicCompliances MODULE-COMPLIANCE
			STATUS current
			DESCRIPTION 
				"Description."
			MODULE -- this module
				MANDATORY-GROUPS { tpu1cGroupIpNet, tpu1cGroupRealTimeClock, tpu1cGroupCommands, tpu1cGroupIOCircuits, tpu1cGroupTelemetry, 
					tpu1cGroupChannelQuality, tpu1cGroupAlarmsStatus, tpu1cGroupEventsStatus, tpu1cGroupReset, tpu1cGroupNotificationsAuxData, 
					tpu1cGroupNotificationsSystemAlarms, tpu1cGroupNotificationsChannelAlarms, tpu1cGroupNotificationsCommands, tpu1cGroupNotificationsTelemetry }
			::= { tpu1cMibCompliances 1 }

		
--   1.3.6.1.4.1.6346.1.8.14
-- 1.3.6.1.4.1.6346.1.8.14
		-- 1.3.6.1.4.1.6346.1.8.14
		tpu1cIocsDataSfp OBJECT IDENTIFIER ::= { tpu1c 14 }

		
--   1.3.6.1.4.1.6346.1.8.14.1
-- 1.3.6.1.4.1.6346.1.8.14.1
		-- 1.3.6.1.4.1.6346.1.8.14.1
		tpu1cInfoIocsSfpManufacturerTable OBJECT-TYPE
			SYNTAX SEQUENCE OF Tpu1cInfoIocsSfpManufacturerEntry
			MAX-ACCESS not-accessible
			STATUS current
			DESCRIPTION
				"Description."
			::= { tpu1cIocsDataSfp 1 }

		
--   1.3.6.1.4.1.6346.1.8.14.1.1
-- 1.3.6.1.4.1.6346.1.8.14.1.1
		-- 1.3.6.1.4.1.6346.1.8.14.1.1
		tpu1cInfoIocsSfpManufacturerEntry OBJECT-TYPE
			SYNTAX Tpu1cInfoIocsSfpManufacturerEntry
			MAX-ACCESS not-accessible
			STATUS current
			DESCRIPTION
				"Description."
			INDEX { tpu1cInfoIocsSfpManufacturerIndex }
			::= { tpu1cInfoIocsSfpManufacturerTable 1 }

		
		Tpu1cInfoIocsSfpManufacturerEntry ::=
			SEQUENCE { 
				tpu1cInfoIocsSfpManufacturerIndex
					Integer32,
				tpu1cInfoIocsSfpManufacturer
					OCTET STRING
			 }

--   1.3.6.1.4.1.6346.1.8.14.1.1.1
-- 1.3.6.1.4.1.6346.1.8.14.1.1.1
		-- 1.3.6.1.4.1.6346.1.8.14.1.1.1
		tpu1cInfoIocsSfpManufacturerIndex OBJECT-TYPE
			SYNTAX Integer32 (1..2)
			MAX-ACCESS not-accessible
			STATUS current
			DESCRIPTION
				"Description."
			::= { tpu1cInfoIocsSfpManufacturerEntry 1 }

		
--   1.3.6.1.4.1.6346.1.8.14.1.1.2
-- 1.3.6.1.4.1.6346.1.8.14.1.1.2
		-- 1.3.6.1.4.1.6346.1.8.14.1.1.2
		tpu1cInfoIocsSfpManufacturer OBJECT-TYPE
			SYNTAX OCTET STRING
			MAX-ACCESS read-only
			STATUS current
			DESCRIPTION
				"Description."
			::= { tpu1cInfoIocsSfpManufacturerEntry 2 }

		
--   1.3.6.1.4.1.6346.1.8.14.2
-- 1.3.6.1.4.1.6346.1.8.14.2
		-- 1.3.6.1.4.1.6346.1.8.14.2
		tpu1cInfoIocsSfpModelTable OBJECT-TYPE
			SYNTAX SEQUENCE OF Tpu1cInfoIocsSfpModelEntry
			MAX-ACCESS not-accessible
			STATUS current
			DESCRIPTION
				"Description."
			::= { tpu1cIocsDataSfp 2 }

		
--   1.3.6.1.4.1.6346.1.8.14.2.1
-- 1.3.6.1.4.1.6346.1.8.14.2.1
		-- 1.3.6.1.4.1.6346.1.8.14.2.1
		tpu1cInfoIocsSfpModelEntry OBJECT-TYPE
			SYNTAX Tpu1cInfoIocsSfpModelEntry
			MAX-ACCESS not-accessible
			STATUS current
			DESCRIPTION
				"Description."
			INDEX { tpu1cInfoIocsSfpModelIndex }
			::= { tpu1cInfoIocsSfpModelTable 1 }

		
		Tpu1cInfoIocsSfpModelEntry ::=
			SEQUENCE { 
				tpu1cInfoIocsSfpModelIndex
					Integer32,
				tpu1cInfoIocsSfpModel
					OCTET STRING
			 }

--   1.3.6.1.4.1.6346.1.8.14.2.1.1
-- 1.3.6.1.4.1.6346.1.8.14.2.1.1
		-- 1.3.6.1.4.1.6346.1.8.14.2.1.1
		tpu1cInfoIocsSfpModelIndex OBJECT-TYPE
			SYNTAX Integer32 (1..2)
			MAX-ACCESS not-accessible
			STATUS current
			DESCRIPTION
				"Description."
			::= { tpu1cInfoIocsSfpModelEntry 1 }

		
--   1.3.6.1.4.1.6346.1.8.14.2.1.2
-- 1.3.6.1.4.1.6346.1.8.14.2.1.2
		-- 1.3.6.1.4.1.6346.1.8.14.2.1.2
		tpu1cInfoIocsSfpModel OBJECT-TYPE
			SYNTAX OCTET STRING
			MAX-ACCESS read-only
			STATUS current
			DESCRIPTION
				"Description."
			::= { tpu1cInfoIocsSfpModelEntry 2 }

		
--   1.3.6.1.4.1.6346.1.8.14.3
-- 1.3.6.1.4.1.6346.1.8.14.3
		-- 1.3.6.1.4.1.6346.1.8.14.3
		tpu1cInfoIocsSfpSerialNumTable OBJECT-TYPE
			SYNTAX SEQUENCE OF Tpu1cInfoIocsSfpSerialNumEntry
			MAX-ACCESS not-accessible
			STATUS current
			DESCRIPTION
				"Description."
			::= { tpu1cIocsDataSfp 3 }

		
--   1.3.6.1.4.1.6346.1.8.14.3.1
-- 1.3.6.1.4.1.6346.1.8.14.3.1
		-- 1.3.6.1.4.1.6346.1.8.14.3.1
		tpu1cInfoIocsSfpSerialNumEntry OBJECT-TYPE
			SYNTAX Tpu1cInfoIocsSfpSerialNumEntry
			MAX-ACCESS not-accessible
			STATUS current
			DESCRIPTION
				"Description."
			INDEX { tpu1cInfoIocsSfpSerialNumIndex }
			::= { tpu1cInfoIocsSfpSerialNumTable 1 }

		
		Tpu1cInfoIocsSfpSerialNumEntry ::=
			SEQUENCE { 
				tpu1cInfoIocsSfpSerialNumIndex
					Integer32,
				tpu1cInfoIocsSfpSerialNum
					OCTET STRING
			 }

--   1.3.6.1.4.1.6346.1.8.14.3.1.1
-- 1.3.6.1.4.1.6346.1.8.14.3.1.1
		-- 1.3.6.1.4.1.6346.1.8.14.3.1.1
		tpu1cInfoIocsSfpSerialNumIndex OBJECT-TYPE
			SYNTAX Integer32 (1..2)
			MAX-ACCESS not-accessible
			STATUS current
			DESCRIPTION
				"Description."
			::= { tpu1cInfoIocsSfpSerialNumEntry 1 }

		
--   1.3.6.1.4.1.6346.1.8.14.3.1.2
-- 1.3.6.1.4.1.6346.1.8.14.3.1.2
		-- 1.3.6.1.4.1.6346.1.8.14.3.1.2
		tpu1cInfoIocsSfpSerialNum OBJECT-TYPE
			SYNTAX OCTET STRING
			MAX-ACCESS read-only
			STATUS current
			DESCRIPTION
				"Description."
			::= { tpu1cInfoIocsSfpSerialNumEntry 2 }

		
--   1.3.6.1.4.1.6346.1.8.14.4
-- 1.3.6.1.4.1.6346.1.8.14.4
		-- 1.3.6.1.4.1.6346.1.8.14.4
		tpu1cInfoIocsSfpRevisionTable OBJECT-TYPE
			SYNTAX SEQUENCE OF Tpu1cInfoIocsSfpRevisionEntry
			MAX-ACCESS not-accessible
			STATUS current
			DESCRIPTION
				"Description."
			::= { tpu1cIocsDataSfp 4 }

		
--   1.3.6.1.4.1.6346.1.8.14.4.1
-- 1.3.6.1.4.1.6346.1.8.14.4.1
		-- 1.3.6.1.4.1.6346.1.8.14.4.1
		tpu1cInfoIocsSfpRevisionEntry OBJECT-TYPE
			SYNTAX Tpu1cInfoIocsSfpRevisionEntry
			MAX-ACCESS not-accessible
			STATUS current
			DESCRIPTION
				"Description."
			INDEX { tpu1cInfoIocsSfpRevisionIndex }
			::= { tpu1cInfoIocsSfpRevisionTable 1 }

		
		Tpu1cInfoIocsSfpRevisionEntry ::=
			SEQUENCE { 
				tpu1cInfoIocsSfpRevisionIndex
					Integer32,
				tpu1cInfoIocsSfpRevision
					OCTET STRING
			 }

--   1.3.6.1.4.1.6346.1.8.14.4.1.1
-- 1.3.6.1.4.1.6346.1.8.14.4.1.1
		-- 1.3.6.1.4.1.6346.1.8.14.4.1.1
		tpu1cInfoIocsSfpRevisionIndex OBJECT-TYPE
			SYNTAX Integer32 (1..2)
			MAX-ACCESS not-accessible
			STATUS current
			DESCRIPTION
				"Description."
			::= { tpu1cInfoIocsSfpRevisionEntry 1 }

		
--   1.3.6.1.4.1.6346.1.8.14.4.1.2
-- 1.3.6.1.4.1.6346.1.8.14.4.1.2
		-- 1.3.6.1.4.1.6346.1.8.14.4.1.2
		tpu1cInfoIocsSfpRevision OBJECT-TYPE
			SYNTAX OCTET STRING
			MAX-ACCESS read-only
			STATUS current
			DESCRIPTION
				"Description."
			::= { tpu1cInfoIocsSfpRevisionEntry 2 }

		
--   1.3.6.1.4.1.6346.1.8.14.5
-- 1.3.6.1.4.1.6346.1.8.14.5
		-- 1.3.6.1.4.1.6346.1.8.14.5
		tpu1cInfoIocsSfpTxMediaTable OBJECT-TYPE
			SYNTAX SEQUENCE OF Tpu1cInfoIocsSfpTxMediaEntry
			MAX-ACCESS not-accessible
			STATUS current
			DESCRIPTION
				"Description."
			::= { tpu1cIocsDataSfp 5 }

		
--   1.3.6.1.4.1.6346.1.8.14.5.1
-- 1.3.6.1.4.1.6346.1.8.14.5.1
		-- 1.3.6.1.4.1.6346.1.8.14.5.1
		tpu1cInfoIocsSfpTxMediaEntry OBJECT-TYPE
			SYNTAX Tpu1cInfoIocsSfpTxMediaEntry
			MAX-ACCESS not-accessible
			STATUS current
			DESCRIPTION
				"Description."
			INDEX { tpu1cInfoIocsSfpTxMediaIndex }
			::= { tpu1cInfoIocsSfpTxMediaTable 1 }

		
		Tpu1cInfoIocsSfpTxMediaEntry ::=
			SEQUENCE { 
				tpu1cInfoIocsSfpTxMediaIndex
					Integer32,
				tpu1cInfoIocsSfpTxMedia
					Unsigned32
			 }

--   1.3.6.1.4.1.6346.1.8.14.5.1.1
-- 1.3.6.1.4.1.6346.1.8.14.5.1.1
		-- 1.3.6.1.4.1.6346.1.8.14.5.1.1
		tpu1cInfoIocsSfpTxMediaIndex OBJECT-TYPE
			SYNTAX Integer32 (1..2)
			MAX-ACCESS not-accessible
			STATUS current
			DESCRIPTION
				"Description."
			::= { tpu1cInfoIocsSfpTxMediaEntry 1 }

		
--   1.3.6.1.4.1.6346.1.8.14.5.1.2
-- 1.3.6.1.4.1.6346.1.8.14.5.1.2
		-- 1.3.6.1.4.1.6346.1.8.14.5.1.2
		tpu1cInfoIocsSfpTxMedia OBJECT-TYPE
			SYNTAX Unsigned32
			MAX-ACCESS read-only
			STATUS current
			DESCRIPTION
				"Description."
			::= { tpu1cInfoIocsSfpTxMediaEntry 2 }

		
--   1.3.6.1.4.1.6346.1.8.14.6
-- 1.3.6.1.4.1.6346.1.8.14.6
		-- 1.3.6.1.4.1.6346.1.8.14.6
		tpu1cInfoIocsSfpConnTypeTable OBJECT-TYPE
			SYNTAX SEQUENCE OF Tpu1cInfoIocsSfpConnTypeEntry
			MAX-ACCESS not-accessible
			STATUS current
			DESCRIPTION
				"Description."
			::= { tpu1cIocsDataSfp 6 }

		
--   1.3.6.1.4.1.6346.1.8.14.6.1
-- 1.3.6.1.4.1.6346.1.8.14.6.1
		-- 1.3.6.1.4.1.6346.1.8.14.6.1
		tpu1cInfoIocsSfpConnTypeEntry OBJECT-TYPE
			SYNTAX Tpu1cInfoIocsSfpConnTypeEntry
			MAX-ACCESS not-accessible
			STATUS current
			DESCRIPTION
				"Description."
			INDEX { tpu1cInfoIocsSfpConnTypeIndex }
			::= { tpu1cInfoIocsSfpConnTypeTable 1 }

		
		Tpu1cInfoIocsSfpConnTypeEntry ::=
			SEQUENCE { 
				tpu1cInfoIocsSfpConnTypeIndex
					Integer32,
				tpu1cInfoIocsSfpConnType
					Unsigned32
			 }

--   1.3.6.1.4.1.6346.1.8.14.6.1.1
-- 1.3.6.1.4.1.6346.1.8.14.6.1.1
		-- 1.3.6.1.4.1.6346.1.8.14.6.1.1
		tpu1cInfoIocsSfpConnTypeIndex OBJECT-TYPE
			SYNTAX Integer32 (1..2)
			MAX-ACCESS not-accessible
			STATUS current
			DESCRIPTION
				"Description."
			::= { tpu1cInfoIocsSfpConnTypeEntry 1 }

		
--   1.3.6.1.4.1.6346.1.8.14.6.1.2
-- 1.3.6.1.4.1.6346.1.8.14.6.1.2
		-- 1.3.6.1.4.1.6346.1.8.14.6.1.2
		tpu1cInfoIocsSfpConnType OBJECT-TYPE
			SYNTAX Unsigned32
			MAX-ACCESS read-only
			STATUS current
			DESCRIPTION
				"Description."
			::= { tpu1cInfoIocsSfpConnTypeEntry 2 }

		
--   1.3.6.1.4.1.6346.1.8.14.7
-- 1.3.6.1.4.1.6346.1.8.14.7
		-- 1.3.6.1.4.1.6346.1.8.14.7
		tpu1cInfoIocsSfpWavelengthTable OBJECT-TYPE
			SYNTAX SEQUENCE OF Tpu1cInfoIocsSfpWavelengthEntry
			MAX-ACCESS not-accessible
			STATUS current
			DESCRIPTION
				"Description."
			::= { tpu1cIocsDataSfp 7 }

		
--   1.3.6.1.4.1.6346.1.8.14.7.1
-- 1.3.6.1.4.1.6346.1.8.14.7.1
		-- 1.3.6.1.4.1.6346.1.8.14.7.1
		tpu1cInfoIocsSfpWavelengthEntry OBJECT-TYPE
			SYNTAX Tpu1cInfoIocsSfpWavelengthEntry
			MAX-ACCESS not-accessible
			STATUS current
			DESCRIPTION
				"Description."
			INDEX { tpu1cInfoIocsSfpWavelengthIndex }
			::= { tpu1cInfoIocsSfpWavelengthTable 1 }

		
		Tpu1cInfoIocsSfpWavelengthEntry ::=
			SEQUENCE { 
				tpu1cInfoIocsSfpWavelengthIndex
					Integer32,
				tpu1cInfoIocsSfpWavelength
					Unsigned32
			 }

--   1.3.6.1.4.1.6346.1.8.14.7.1.1
-- 1.3.6.1.4.1.6346.1.8.14.7.1.1
		-- 1.3.6.1.4.1.6346.1.8.14.7.1.1
		tpu1cInfoIocsSfpWavelengthIndex OBJECT-TYPE
			SYNTAX Integer32 (1..2)
			MAX-ACCESS not-accessible
			STATUS current
			DESCRIPTION
				"Description."
			::= { tpu1cInfoIocsSfpWavelengthEntry 1 }

		
--   1.3.6.1.4.1.6346.1.8.14.7.1.2
-- 1.3.6.1.4.1.6346.1.8.14.7.1.2
		-- 1.3.6.1.4.1.6346.1.8.14.7.1.2
		tpu1cInfoIocsSfpWavelength OBJECT-TYPE
			SYNTAX Unsigned32
			MAX-ACCESS read-only
			STATUS current
			DESCRIPTION
				"Description."
			::= { tpu1cInfoIocsSfpWavelengthEntry 2 }

		
--   1.3.6.1.4.1.6346.1.8.14.8
-- 1.3.6.1.4.1.6346.1.8.14.8
		-- 1.3.6.1.4.1.6346.1.8.14.8
		tpu1cInfoIocsSfpRange9mmTable OBJECT-TYPE
			SYNTAX SEQUENCE OF Tpu1cInfoIocsSfpRange9mmEntry
			MAX-ACCESS not-accessible
			STATUS current
			DESCRIPTION
				"Description."
			::= { tpu1cIocsDataSfp 8 }

		
--   1.3.6.1.4.1.6346.1.8.14.8.1
-- 1.3.6.1.4.1.6346.1.8.14.8.1
		-- 1.3.6.1.4.1.6346.1.8.14.8.1
		tpu1cInfoIocsSfpRange9mmEntry OBJECT-TYPE
			SYNTAX Tpu1cInfoIocsSfpRange9mmEntry
			MAX-ACCESS not-accessible
			STATUS current
			DESCRIPTION
				"Description."
			INDEX { tpu1cInfoIocsSfpRange9mmIndex }
			::= { tpu1cInfoIocsSfpRange9mmTable 1 }

		
		Tpu1cInfoIocsSfpRange9mmEntry ::=
			SEQUENCE { 
				tpu1cInfoIocsSfpRange9mmIndex
					Integer32,
				tpu1cInfoIocsSfpRange9mm
					Unsigned32
			 }

--   1.3.6.1.4.1.6346.1.8.14.8.1.1
-- 1.3.6.1.4.1.6346.1.8.14.8.1.1
		-- 1.3.6.1.4.1.6346.1.8.14.8.1.1
		tpu1cInfoIocsSfpRange9mmIndex OBJECT-TYPE
			SYNTAX Integer32 (1..2)
			MAX-ACCESS not-accessible
			STATUS current
			DESCRIPTION
				"Description."
			::= { tpu1cInfoIocsSfpRange9mmEntry 1 }

		
--   1.3.6.1.4.1.6346.1.8.14.8.1.2
-- 1.3.6.1.4.1.6346.1.8.14.8.1.2
		-- 1.3.6.1.4.1.6346.1.8.14.8.1.2
		tpu1cInfoIocsSfpRange9mm OBJECT-TYPE
			SYNTAX Unsigned32
			MAX-ACCESS read-only
			STATUS current
			DESCRIPTION
				"Description."
			::= { tpu1cInfoIocsSfpRange9mmEntry 2 }

		
--   1.3.6.1.4.1.6346.1.8.14.9
-- 1.3.6.1.4.1.6346.1.8.14.9
		-- 1.3.6.1.4.1.6346.1.8.14.9
		tpu1cInfoIocsSfpRange50mmTable OBJECT-TYPE
			SYNTAX SEQUENCE OF Tpu1cInfoIocsSfpRange50mmEntry
			MAX-ACCESS not-accessible
			STATUS current
			DESCRIPTION
				"Description."
			::= { tpu1cIocsDataSfp 9 }

		
--   1.3.6.1.4.1.6346.1.8.14.9.1
-- 1.3.6.1.4.1.6346.1.8.14.9.1
		-- 1.3.6.1.4.1.6346.1.8.14.9.1
		tpu1cInfoIocsSfpRange50mmEntry OBJECT-TYPE
			SYNTAX Tpu1cInfoIocsSfpRange50mmEntry
			MAX-ACCESS not-accessible
			STATUS current
			DESCRIPTION
				"Description."
			INDEX { tpu1cInfoIocsSfpRange50mmIndex }
			::= { tpu1cInfoIocsSfpRange50mmTable 1 }

		
		Tpu1cInfoIocsSfpRange50mmEntry ::=
			SEQUENCE { 
				tpu1cInfoIocsSfpRange50mmIndex
					Integer32,
				tpu1cInfoIocsSfpRange50mm
					Unsigned32
			 }

--   1.3.6.1.4.1.6346.1.8.14.9.1.1
-- 1.3.6.1.4.1.6346.1.8.14.9.1.1
		-- 1.3.6.1.4.1.6346.1.8.14.9.1.1
		tpu1cInfoIocsSfpRange50mmIndex OBJECT-TYPE
			SYNTAX Integer32 (1..2)
			MAX-ACCESS not-accessible
			STATUS current
			DESCRIPTION
				"Description."
			::= { tpu1cInfoIocsSfpRange50mmEntry 1 }

		
--   1.3.6.1.4.1.6346.1.8.14.9.1.2
-- 1.3.6.1.4.1.6346.1.8.14.9.1.2
		-- 1.3.6.1.4.1.6346.1.8.14.9.1.2
		tpu1cInfoIocsSfpRange50mm OBJECT-TYPE
			SYNTAX Unsigned32
			MAX-ACCESS read-only
			STATUS current
			DESCRIPTION
				"Description."
			::= { tpu1cInfoIocsSfpRange50mmEntry 2 }

		
--   1.3.6.1.4.1.6346.1.8.14.10
-- 1.3.6.1.4.1.6346.1.8.14.10
		-- 1.3.6.1.4.1.6346.1.8.14.10
		tpu1cInfoIocsSfpRange62mm5Table OBJECT-TYPE
			SYNTAX SEQUENCE OF Tpu1cInfoIocsSfpRange62mm5Entry
			MAX-ACCESS not-accessible
			STATUS current
			DESCRIPTION
				"Description."
			::= { tpu1cIocsDataSfp 10 }

		
--   1.3.6.1.4.1.6346.1.8.14.10.1
-- 1.3.6.1.4.1.6346.1.8.14.10.1
		-- 1.3.6.1.4.1.6346.1.8.14.10.1
		tpu1cInfoIocsSfpRange62mm5Entry OBJECT-TYPE
			SYNTAX Tpu1cInfoIocsSfpRange62mm5Entry
			MAX-ACCESS not-accessible
			STATUS current
			DESCRIPTION
				"Description."
			INDEX { tpu1cInfoIocsSfpRange62mm5Index }
			::= { tpu1cInfoIocsSfpRange62mm5Table 1 }

		
		Tpu1cInfoIocsSfpRange62mm5Entry ::=
			SEQUENCE { 
				tpu1cInfoIocsSfpRange62mm5Index
					Integer32,
				tpu1cInfoIocsSfpRange62mm5
					Unsigned32
			 }

--   1.3.6.1.4.1.6346.1.8.14.10.1.1
-- 1.3.6.1.4.1.6346.1.8.14.10.1.1
		-- 1.3.6.1.4.1.6346.1.8.14.10.1.1
		tpu1cInfoIocsSfpRange62mm5Index OBJECT-TYPE
			SYNTAX Integer32 (1..2)
			MAX-ACCESS not-accessible
			STATUS current
			DESCRIPTION
				"Description."
			::= { tpu1cInfoIocsSfpRange62mm5Entry 1 }

		
--   1.3.6.1.4.1.6346.1.8.14.10.1.2
-- 1.3.6.1.4.1.6346.1.8.14.10.1.2
		-- 1.3.6.1.4.1.6346.1.8.14.10.1.2
		tpu1cInfoIocsSfpRange62mm5 OBJECT-TYPE
			SYNTAX Unsigned32
			MAX-ACCESS read-only
			STATUS current
			DESCRIPTION
				"Description."
			::= { tpu1cInfoIocsSfpRange62mm5Entry 2 }

		
--   1.3.6.1.4.1.6346.1.8.14.11
-- 1.3.6.1.4.1.6346.1.8.14.11
		-- 1.3.6.1.4.1.6346.1.8.14.11
		tpu1cInfoIocsSfpRangeCopperTable OBJECT-TYPE
			SYNTAX SEQUENCE OF Tpu1cInfoIocsSfpRangeCopperEntry
			MAX-ACCESS not-accessible
			STATUS current
			DESCRIPTION
				"Description."
			::= { tpu1cIocsDataSfp 11 }

		
--   1.3.6.1.4.1.6346.1.8.14.11.1
-- 1.3.6.1.4.1.6346.1.8.14.11.1
		-- 1.3.6.1.4.1.6346.1.8.14.11.1
		tpu1cInfoIocsSfpRangeCopperEntry OBJECT-TYPE
			SYNTAX Tpu1cInfoIocsSfpRangeCopperEntry
			MAX-ACCESS not-accessible
			STATUS current
			DESCRIPTION
				"Description."
			INDEX { tpu1cInfoIocsSfpRangeCopperIndex }
			::= { tpu1cInfoIocsSfpRangeCopperTable 1 }

		
		Tpu1cInfoIocsSfpRangeCopperEntry ::=
			SEQUENCE { 
				tpu1cInfoIocsSfpRangeCopperIndex
					Integer32,
				tpu1cInfoIocsSfpRangeCopper
					Unsigned32
			 }

--   1.3.6.1.4.1.6346.1.8.14.11.1.1
-- 1.3.6.1.4.1.6346.1.8.14.11.1.1
		-- 1.3.6.1.4.1.6346.1.8.14.11.1.1
		tpu1cInfoIocsSfpRangeCopperIndex OBJECT-TYPE
			SYNTAX Integer32 (1..2)
			MAX-ACCESS not-accessible
			STATUS current
			DESCRIPTION
				"Description."
			::= { tpu1cInfoIocsSfpRangeCopperEntry 1 }

		
--   1.3.6.1.4.1.6346.1.8.14.11.1.2
-- 1.3.6.1.4.1.6346.1.8.14.11.1.2
		-- 1.3.6.1.4.1.6346.1.8.14.11.1.2
		tpu1cInfoIocsSfpRangeCopper OBJECT-TYPE
			SYNTAX Unsigned32
			MAX-ACCESS read-only
			STATUS current
			DESCRIPTION
				"Description."
			::= { tpu1cInfoIocsSfpRangeCopperEntry 2 }

		
--   1.3.6.1.4.1.6346.1.8.14.12
-- 1.3.6.1.4.1.6346.1.8.14.12
		-- 1.3.6.1.4.1.6346.1.8.14.12
		tpu1cMeasIocsSfpTemperatureTable OBJECT-TYPE
			SYNTAX SEQUENCE OF Tpu1cMeasIocsSfpTemperatureEntry
			MAX-ACCESS not-accessible
			STATUS current
			DESCRIPTION
				"Description."
			::= { tpu1cIocsDataSfp 12 }

		
--   1.3.6.1.4.1.6346.1.8.14.12.1
-- 1.3.6.1.4.1.6346.1.8.14.12.1
		-- 1.3.6.1.4.1.6346.1.8.14.12.1
		tpu1cMeasIocsSfpTemperatureEntry OBJECT-TYPE
			SYNTAX Tpu1cMeasIocsSfpTemperatureEntry
			MAX-ACCESS not-accessible
			STATUS current
			DESCRIPTION
				"Description."
			INDEX { tpu1cMeasIocsSfpTemperatureIndex }
			::= { tpu1cMeasIocsSfpTemperatureTable 1 }

		
		Tpu1cMeasIocsSfpTemperatureEntry ::=
			SEQUENCE { 
				tpu1cMeasIocsSfpTemperatureIndex
					Integer32,
				tpu1cMeasIocsSfpTemperature
					Unsigned32
			 }

--   1.3.6.1.4.1.6346.1.8.14.12.1.1
-- 1.3.6.1.4.1.6346.1.8.14.12.1.1
		-- 1.3.6.1.4.1.6346.1.8.14.12.1.1
		tpu1cMeasIocsSfpTemperatureIndex OBJECT-TYPE
			SYNTAX Integer32 (1..2)
			MAX-ACCESS not-accessible
			STATUS current
			DESCRIPTION
				"Description."
			::= { tpu1cMeasIocsSfpTemperatureEntry 1 }

		
--   1.3.6.1.4.1.6346.1.8.14.12.1.2
-- 1.3.6.1.4.1.6346.1.8.14.12.1.2
		-- 1.3.6.1.4.1.6346.1.8.14.12.1.2
		tpu1cMeasIocsSfpTemperature OBJECT-TYPE
			SYNTAX Unsigned32
			MAX-ACCESS read-only
			STATUS current
			DESCRIPTION
				"Description."
			::= { tpu1cMeasIocsSfpTemperatureEntry 2 }

		
--   1.3.6.1.4.1.6346.1.8.14.13
-- 1.3.6.1.4.1.6346.1.8.14.13
		-- 1.3.6.1.4.1.6346.1.8.14.13
		tpu1cMeasIocsSfpVccTable OBJECT-TYPE
			SYNTAX SEQUENCE OF Tpu1cMeasIocsSfpVccEntry
			MAX-ACCESS not-accessible
			STATUS current
			DESCRIPTION
				"Description."
			::= { tpu1cIocsDataSfp 13 }

		
--   1.3.6.1.4.1.6346.1.8.14.13.1
-- 1.3.6.1.4.1.6346.1.8.14.13.1
		-- 1.3.6.1.4.1.6346.1.8.14.13.1
		tpu1cMeasIocsSfpVccEntry OBJECT-TYPE
			SYNTAX Tpu1cMeasIocsSfpVccEntry
			MAX-ACCESS not-accessible
			STATUS current
			DESCRIPTION
				"Description."
			INDEX { tpu1cMeasIocsSfpVccIndex }
			::= { tpu1cMeasIocsSfpVccTable 1 }

		
		Tpu1cMeasIocsSfpVccEntry ::=
			SEQUENCE { 
				tpu1cMeasIocsSfpVccIndex
					Integer32,
				tpu1cMeasIocsSfpVcc
					Unsigned32
			 }

--   1.3.6.1.4.1.6346.1.8.14.13.1.1
-- 1.3.6.1.4.1.6346.1.8.14.13.1.1
		-- 1.3.6.1.4.1.6346.1.8.14.13.1.1
		tpu1cMeasIocsSfpVccIndex OBJECT-TYPE
			SYNTAX Integer32 (1..2)
			MAX-ACCESS not-accessible
			STATUS current
			DESCRIPTION
				"Description."
			::= { tpu1cMeasIocsSfpVccEntry 1 }

		
--   1.3.6.1.4.1.6346.1.8.14.13.1.2
-- 1.3.6.1.4.1.6346.1.8.14.13.1.2
		-- 1.3.6.1.4.1.6346.1.8.14.13.1.2
		tpu1cMeasIocsSfpVcc OBJECT-TYPE
			SYNTAX Unsigned32
			MAX-ACCESS read-only
			STATUS current
			DESCRIPTION
				"Description."
			::= { tpu1cMeasIocsSfpVccEntry 2 }

		
--   1.3.6.1.4.1.6346.1.8.14.14
-- 1.3.6.1.4.1.6346.1.8.14.14
		-- 1.3.6.1.4.1.6346.1.8.14.14
		tpu1cMeasIocsSfpTxBiasTable OBJECT-TYPE
			SYNTAX SEQUENCE OF Tpu1cMeasIocsSfpTxBiasEntry
			MAX-ACCESS not-accessible
			STATUS current
			DESCRIPTION
				"Description."
			::= { tpu1cIocsDataSfp 14 }

		
--   1.3.6.1.4.1.6346.1.8.14.14.1
-- 1.3.6.1.4.1.6346.1.8.14.14.1
		-- 1.3.6.1.4.1.6346.1.8.14.14.1
		tpu1cMeasIocsSfpTxBiasEntry OBJECT-TYPE
			SYNTAX Tpu1cMeasIocsSfpTxBiasEntry
			MAX-ACCESS not-accessible
			STATUS current
			DESCRIPTION
				"Description."
			INDEX { tpu1cMeasIocsSfpTxBiasIndex }
			::= { tpu1cMeasIocsSfpTxBiasTable 1 }

		
		Tpu1cMeasIocsSfpTxBiasEntry ::=
			SEQUENCE { 
				tpu1cMeasIocsSfpTxBiasIndex
					Integer32,
				tpu1cMeasIocsSfpTxBias
					Unsigned32
			 }

--   1.3.6.1.4.1.6346.1.8.14.14.1.1
-- 1.3.6.1.4.1.6346.1.8.14.14.1.1
		-- 1.3.6.1.4.1.6346.1.8.14.14.1.1
		tpu1cMeasIocsSfpTxBiasIndex OBJECT-TYPE
			SYNTAX Integer32 (1..2)
			MAX-ACCESS not-accessible
			STATUS current
			DESCRIPTION
				"Description."
			::= { tpu1cMeasIocsSfpTxBiasEntry 1 }

		
--   1.3.6.1.4.1.6346.1.8.14.14.1.2
-- 1.3.6.1.4.1.6346.1.8.14.14.1.2
		-- 1.3.6.1.4.1.6346.1.8.14.14.1.2
		tpu1cMeasIocsSfpTxBias OBJECT-TYPE
			SYNTAX Unsigned32
			MAX-ACCESS read-only
			STATUS current
			DESCRIPTION
				"Description."
			::= { tpu1cMeasIocsSfpTxBiasEntry 2 }

		
--   1.3.6.1.4.1.6346.1.8.14.15
-- 1.3.6.1.4.1.6346.1.8.14.15
		-- 1.3.6.1.4.1.6346.1.8.14.15
		tpu1cMeasIocsSfpTxPowerTable OBJECT-TYPE
			SYNTAX SEQUENCE OF Tpu1cMeasIocsSfpTxPowerEntry
			MAX-ACCESS not-accessible
			STATUS current
			DESCRIPTION
				"Description."
			::= { tpu1cIocsDataSfp 15 }

		
--   1.3.6.1.4.1.6346.1.8.14.15.1
-- 1.3.6.1.4.1.6346.1.8.14.15.1
		-- 1.3.6.1.4.1.6346.1.8.14.15.1
		tpu1cMeasIocsSfpTxPowerEntry OBJECT-TYPE
			SYNTAX Tpu1cMeasIocsSfpTxPowerEntry
			MAX-ACCESS not-accessible
			STATUS current
			DESCRIPTION
				"Description."
			INDEX { tpu1cMeasIocsSfpTxPowerIndex }
			::= { tpu1cMeasIocsSfpTxPowerTable 1 }

		
		Tpu1cMeasIocsSfpTxPowerEntry ::=
			SEQUENCE { 
				tpu1cMeasIocsSfpTxPowerIndex
					Integer32,
				tpu1cMeasIocsSfpTxPower
					Unsigned32
			 }

--   1.3.6.1.4.1.6346.1.8.14.15.1.1
-- 1.3.6.1.4.1.6346.1.8.14.15.1.1
		-- 1.3.6.1.4.1.6346.1.8.14.15.1.1
		tpu1cMeasIocsSfpTxPowerIndex OBJECT-TYPE
			SYNTAX Integer32 (1..2)
			MAX-ACCESS not-accessible
			STATUS current
			DESCRIPTION
				"Description."
			::= { tpu1cMeasIocsSfpTxPowerEntry 1 }

		
--   1.3.6.1.4.1.6346.1.8.14.15.1.2
-- 1.3.6.1.4.1.6346.1.8.14.15.1.2
		-- 1.3.6.1.4.1.6346.1.8.14.15.1.2
		tpu1cMeasIocsSfpTxPower OBJECT-TYPE
			SYNTAX Unsigned32
			MAX-ACCESS read-only
			STATUS current
			DESCRIPTION
				"Description."
			::= { tpu1cMeasIocsSfpTxPowerEntry 2 }

		
--   1.3.6.1.4.1.6346.1.8.14.16
-- 1.3.6.1.4.1.6346.1.8.14.16
		-- 1.3.6.1.4.1.6346.1.8.14.16
		tpu1cMeasIocsSfpRxPowerTable OBJECT-TYPE
			SYNTAX SEQUENCE OF Tpu1cMeasIocsSfpRxPowerEntry
			MAX-ACCESS not-accessible
			STATUS current
			DESCRIPTION
				"Description."
			::= { tpu1cIocsDataSfp 16 }

		
--   1.3.6.1.4.1.6346.1.8.14.16.1
-- 1.3.6.1.4.1.6346.1.8.14.16.1
		-- 1.3.6.1.4.1.6346.1.8.14.16.1
		tpu1cMeasIocsSfpRxPowerEntry OBJECT-TYPE
			SYNTAX Tpu1cMeasIocsSfpRxPowerEntry
			MAX-ACCESS not-accessible
			STATUS current
			DESCRIPTION
				"Description."
			INDEX { tpu1cMeasIocsSfpRxPowerIndex }
			::= { tpu1cMeasIocsSfpRxPowerTable 1 }

		
		Tpu1cMeasIocsSfpRxPowerEntry ::=
			SEQUENCE { 
				tpu1cMeasIocsSfpRxPowerIndex
					Integer32,
				tpu1cMeasIocsSfpRxPower
					Unsigned32
			 }

--   1.3.6.1.4.1.6346.1.8.14.16.1.1
-- 1.3.6.1.4.1.6346.1.8.14.16.1.1
		-- 1.3.6.1.4.1.6346.1.8.14.16.1.1
		tpu1cMeasIocsSfpRxPowerIndex OBJECT-TYPE
			SYNTAX Integer32 (1..2)
			MAX-ACCESS not-accessible
			STATUS current
			DESCRIPTION
				"Description."
			::= { tpu1cMeasIocsSfpRxPowerEntry 1 }

		
--   1.3.6.1.4.1.6346.1.8.14.16.1.2
-- 1.3.6.1.4.1.6346.1.8.14.16.1.2
		-- 1.3.6.1.4.1.6346.1.8.14.16.1.2
		tpu1cMeasIocsSfpRxPower OBJECT-TYPE
			SYNTAX Unsigned32
			MAX-ACCESS read-only
			STATUS current
			DESCRIPTION
				"Description."
			::= { tpu1cMeasIocsSfpRxPowerEntry 2 }

		
--   1.3.6.1.4.1.6346.1.8.15
-- 1.3.6.1.4.1.6346.1.8.15
		-- 1.3.6.1.4.1.6346.1.8.15
		tpu1cCodeVersions OBJECT IDENTIFIER ::= { tpu1c 15 }

		
--   1.3.6.1.4.1.6346.1.8.15.1
-- 1.3.6.1.4.1.6346.1.8.15.1
		-- 1.3.6.1.4.1.6346.1.8.15.1
		tpu1cTpu1z01Version OBJECT-TYPE
			SYNTAX Unsigned32
			MAX-ACCESS read-only
			STATUS current
			DESCRIPTION
				"Description."
			::= { tpu1cCodeVersions 1 }

		
--   1.3.6.1.4.1.6346.1.8.15.2
-- 1.3.6.1.4.1.6346.1.8.15.2
		-- 1.3.6.1.4.1.6346.1.8.15.2
		tpu1cTpu1z02Version OBJECT-TYPE
			SYNTAX Unsigned32
			MAX-ACCESS read-only
			STATUS current
			DESCRIPTION
				"Description."
			::= { tpu1cCodeVersions 2 }

		
--   1.3.6.1.4.1.6346.1.8.15.3
-- 1.3.6.1.4.1.6346.1.8.15.3
		-- 1.3.6.1.4.1.6346.1.8.15.3
		tpu1cTpu1z03Version OBJECT-TYPE
			SYNTAX Unsigned32
			MAX-ACCESS read-only
			STATUS current
			DESCRIPTION
				"Description."
			::= { tpu1cCodeVersions 3 }

		
--   1.3.6.1.4.1.6346.1.8.15.4
-- 1.3.6.1.4.1.6346.1.8.15.4
		-- 1.3.6.1.4.1.6346.1.8.15.4
		tpu1cTpu1z04Version OBJECT-TYPE
			SYNTAX Unsigned32
			MAX-ACCESS read-only
			STATUS current
			DESCRIPTION
				"Description."
			::= { tpu1cCodeVersions 4 }

		
--   1.3.6.1.4.1.6346.1.8.15.5
-- 1.3.6.1.4.1.6346.1.8.15.5
		-- 1.3.6.1.4.1.6346.1.8.15.5
		tpu1cTpu1z05Version OBJECT-TYPE
			SYNTAX Unsigned32
			MAX-ACCESS read-only
			STATUS current
			DESCRIPTION
				"Description."
			::= { tpu1cCodeVersions 5 }

		
	
	END

--
-- DIMAT-TPU1C-MIB.my
--
