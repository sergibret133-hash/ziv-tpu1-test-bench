--
-- DIMAT-BASE-MIB.my
-- MIB generated by MG-SOFT Visual MIB Builder Version 7.0  Build 240
-- Wednesday, April 07, 2021 at 12:22:48
--

	DIMAT-BASE-MIB DEFINITIONS ::= BEGIN
 
		IMPORTS
			enterprises, Integer32, Unsigned32, MODULE-IDENTITY			
				FROM SNMPv2-SMI			
			TEXTUAL-CONVENTION			
				FROM SNMPv2-TC;
	
	
		-- 1.3.6.1.4.1.6346
		dimat MODULE-IDENTITY 
			LAST-UPDATED "202104071156Z"		-- April 07, 2021 at 11:56 GMT
			ORGANIZATION 
				"ZIV Aplicaciones y Tecnología S.L.U."
			CONTACT-INFO 
				"Email:  ziv@zivautomation.com
                Phone:  +34 94 452 2003
                Web:     www.zivautomation.com"
			DESCRIPTION 
				"The Structure of Management Information for Dimat enterprise."
			REVISION "202104071213Z"		-- April 07, 2021 at 12:13 GMT
			DESCRIPTION 
				"Objects for ZIV-DIMAT TPU-1 teleprotection terminal management"
			REVISION "200605181325Z"		-- May 18, 2006 at 13:25 GMT
			DESCRIPTION 
				"0.0.1"
			::= { enterprises 6346 }

		
	
--
-- Textual conventions
--
	
		DataU8 ::= TEXTUAL-CONVENTION
			STATUS current
			DESCRIPTION 
				"DataU8"
			SYNTAX Unsigned32 (0..255)

		DataU16 ::= TEXTUAL-CONVENTION
			STATUS current
			DESCRIPTION 
				"DataU16"
			SYNTAX Integer32 (0..65535)

		DataU32 ::= TEXTUAL-CONVENTION
			STATUS current
			DESCRIPTION 
				"DataU32"
			SYNTAX Unsigned32

		DataBool ::= TEXTUAL-CONVENTION
			STATUS current
			DESCRIPTION 
				"DataBool"
			SYNTAX INTEGER
				{
				false(0),
				true(1)
				}

		DataFloat ::= TEXTUAL-CONVENTION
			STATUS current
			DESCRIPTION 
				"DataFloat"
			SYNTAX Unsigned32

		DataString ::= TEXTUAL-CONVENTION
			STATUS current
			DESCRIPTION 
				"DataString"
			SYNTAX OCTET STRING (SIZE (0..255))

		DataBytes ::= TEXTUAL-CONVENTION
			STATUS current
			DESCRIPTION 
				"DataBytes"
			SYNTAX OCTET STRING (SIZE (0..255))

	
--
-- Node definitions
--
	
		-- 1.3.6.1.4.1.6346.1
		dimatProducts OBJECT IDENTIFIER ::= { dimat 1 }

		
		-- 1.3.6.1.4.1.6346.2
		dimatAgent OBJECT IDENTIFIER ::= { dimat 2 }

		
		-- 1.3.6.1.4.1.6346.3
		dimatTraps OBJECT IDENTIFIER ::= { dimat 3 }

		
		-- 1.3.6.1.4.1.6346.4
		dimatMisc OBJECT IDENTIFIER ::= { dimat 4 }

		
		-- 1.3.6.1.4.1.6346.5
		dimatSignal OBJECT IDENTIFIER ::= { dimat 5 }

		
	
	END

--
-- DIMAT-BASE-MIB.my
--
